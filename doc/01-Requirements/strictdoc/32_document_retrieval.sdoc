[DOCUMENT]
TITLE: Document Retrieval Requirements
UID: GHOST-REQ-DOCUMENT-RETRIEVAL
VERSION: 0.1-dummy
OPTIONS:
  MARKUP: Text
  AUTO_LEVELS: On
  NODE_IN_TOC: True

[[SECTION]]
TITLE: Placeholder

[TEXT]
STATEMENT: >>>
This is a placeholder child requirements document for GHOST document retrieval.

Planned scope:
- project-aware retrieval
- dense retrieval
- SPLADE sparse retrieval where enabled
- hybrid scoring
- retrieval candidates
- document-only retrieval boundary

Detailed atomic requirements shall be added later after human approval.
<<<

[[/SECTION]]

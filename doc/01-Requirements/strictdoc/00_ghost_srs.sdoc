[DOCUMENT]
TITLE: GHOST Software Requirements Specification
UID: GHOST-SRS
VERSION: 0.6-draft
ROOT: True
OPTIONS:
  MARKUP: Text
  AUTO_LEVELS: On
  NODE_IN_TOC: True

[[SECTION]]
TITLE: 1. Introduction

[[SECTION]]
TITLE: 1.1 Purpose

[TEXT]
STATEMENT: >>>
This document is the root Software Requirements Specification for GHOST.

GHOST means GenAI Hybrid Orchestrator for Software Tooling.

GHOST is a human-controlled AI orchestration platform for software engineering. It combines deterministic and heuristic context-engineering methods with LLM-based agents, project retrieval, reusable engineering memory, and external AI tooling in one controlled workflow.

This root SRS defines the product-level scope, professional SRS structure, root requirement anchors, naming policy, traceability direction, current-vs-future boundary, and proposed child-file ownership map for the future StrictDoc requirement tree.

This root SRS is not intended to repeat every detailed subsystem requirement. Detailed atomic requirements shall live in child StrictDoc files after explicit human approval of the requirement-file tree and source-of-truth cutover.
<<<

[[/SECTION]]

[[SECTION]]
TITLE: 1.2 Product Identity and Motivation

[TEXT]
STATEMENT: >>>
GHOST exists because long-running AI-assisted software engineering work needs more control than public AI interfaces normally expose.

Public AI platforms such as ChatGPT UI, Codex, Copilot, Claude, and similar tools can provide strong model-side capabilities. They can support coding, repository interaction, reasoning, document analysis, and other advanced workflows.

At the same time, project-level engineering work needs deterministic control over context, memory, retrieval, selected evidence, hard rules, model-bound information, ignored information, stored information, and excluded information.

GHOST is not defined as a replacement for public AI platforms. GHOST is defined as the surrounding engineering-control layer: project-specific orchestration, structured memory, controlled retrieval, hard rules direction, metadata, auditability, and customizable specialist agents.
<<<

[[/SECTION]]

[[SECTION]]
TITLE: 1.3 Scope

[TEXT]
STATEMENT: >>>
The GHOST product scope covered by this SRS includes:

- engineered prompt construction,
- deterministic preprocessing,
- prompt shaping,
- SuperPrompt state management,
- current GUI-visible prompt rendering through SuperPromptProjector,
- project document ingestion,
- project document retrieval,
- document reranking,
- A3 usefulness gating,
- A4 context condensation,
- reusable engineering memory,
- optional memory retrieval inside the current Retrieval stage,
- memory merge and ActiveBrief direction,
- GUI-based human control,
- structured logging direction,
- documented current AWS runtime deployment,
- MCP interface for approved external AI clients, including Prompt Engineering and approved memory capabilities,
- future requirement-architecture-code-test traceability direction.

The root SRS distinguishes current executable behavior from target architecture and future vision.

The conceptual target pipeline is:

A0_PreProcessing -> A2_PromptShaper -> Retrieval -> ReRanker -> A3_NLI_Gate -> A4_Condenser -> A5_Format_Enforcer -> Prompt_Builder

The current executable GUI runner is more limited:

PreProcessing -> A2 -> Retrieval -> ReRanker or pass-through -> A3 -> A4

Current final prompt rendering is performed through SuperPromptProjector and SuperPrompt prompt-ready composition. The dedicated Prompt Builder/send-boundary remains incomplete and shall not be described as fully implemented.
<<<

[[/SECTION]]

[[SECTION]]
TITLE: 1.4 Intended Audience and Intended Use

[TEXT]
STATEMENT: >>>
This root SRS is intended for:

- the human maintainer of GHOST,
- future development agents,
- future audit agents,
- future requirement-architecture-code synchronization agents,
- architecture reviewers,
- implementation reviewers,
- test and validation planning,
- deployment and operations planning,
- future contributors who need to understand the requirement tree before changing code.

This root SRS shall be used as the navigation and governance root for the requirement system.

The first intended use is migration control: converting existing Markdown requirements into a stable StrictDoc requirement tree without losing product intent, implementation truth, or human control.

The second intended use is future traceability preparation: stable requirement UIDs may later be connected to architecture artifacts, code markers, and tests.
<<<

[[/SECTION]]

[[SECTION]]
TITLE: 1.5 Definitions and Acronyms

[TEXT]
STATEMENT: >>>
GHOST:
GenAI Hybrid Orchestrator for Software Tooling. The product name.

ragstream/:
The current legacy Python package directory inside the repository. It is an implementation namespace, not the product identity. New requirement language shall use GHOST as the product name.

RAGstream:
Historical product/repository wording in older documents. Existing pre-cutover documents may still contain this name as legacy evidence. New or migrated StrictDoc requirements shall use GHOST unless specifically referring to legacy naming.

SuperPrompt:
The central structured runtime representation of the current task, prompt configuration, selected document context, memory context, stage state, diagnostics, and prompt-ready rendering.

SuperPromptProjector:
The current component responsible for GUI-visible engineered prompt rendering and prompt-ready composition.

Controller:
The orchestration component that owns the active SuperPrompt for a session, runs legal pipeline stages, manages project context, and returns updated state to the GUI.

Agent Stack:
The JSON-configured agent infrastructure consisting of AgentFactory, AgentPrompt, llm_client, structured output parsing, and executable agent modes.

AgentFactory:
The component that loads and validates agent configuration and creates concrete agent prompt objects.

AgentPrompt:
The neutral prompt-composition component that combines static agent purpose, enum catalogs, runtime payload, and task instructions.

llm_client:
The LLM provider abstraction currently used for external model API calls and intended to keep model-provider details out of Controller and GUI code.

Executable AgentPrompt modes:
The current executable compose modes are selector, classifier, and synthesizer. Chooser and multi-chooser are aliases or design vocabulary mapped into current executable modes. Writer and Extractor shall not be claimed as live compose modes unless supported by child requirements and code evidence.

A0:
Deterministic preprocessing stage.

A2:
PromptShaper stage that selects prompt meta-settings such as system role, audience, tone, depth, and confidence.

A3:
Usefulness gate stage for retrieved document candidates and comparison context.

A4:
Context condenser stage for selected document evidence.

A5:
Format Enforcer direction. It is reserved/postponed and has no completed live controller action in the current executable runner.

Prompt Builder:
Target final prompt-assembly/send-boundary concept. The dedicated prompt_builder.py path is not the current complete rendering authority. Current visible rendering is through SuperPromptProjector.

Hard Rules:
Planned governance/enforcement direction. Current code contains placeholders and UI/status direction, not a completed hard-rule engine.

Direct LLM Call:
Optional future send-boundary direction. Current supported core path is engineered prompt generation and display, with manual copy/use in external tools.

Document Knowledge:
The document ingestion, retrieval, reranking, evidence-selection, and document-condensation capability area.

Memory System:
The durable memory recording, memory ingestion, memory retrieval, ActiveBrief, memory merge, and memory file/import capability area.

ActiveBrief:
A compact memory or topic-direction artifact used to guide memory-related retrieval, relation classification, or comparison-context construction.

MemoryRecord:
A durable recorded memory unit stored through the memory system.

UID:
Stable unique requirement identifier.

StrictDoc:
The requirements documentation system used for the future requirement source-of-truth tree.

Ghost2:
Future product vision for human-mediated multi-brain orchestration, shared board behavior, shared memory, and deterministic requirement-architecture-code-test traceability.

MCP:
Model Context Protocol. The protocol used by the GHOST MCP interface through which approved external AI clients invoke explicitly exposed GHOST capabilities. Common MCP behavior belongs to 110_mcp.sdoc; Prompt Engineering and non-ActiveBlackboard memory capabilities belong to 111_mcp_capabilities.sdoc; all current and future ActiveBlackboard behavior belongs to 112_mcp_activeblackboard.sdoc.

AWS:
Amazon Web Services runtime environment used by the documented current deployment and the approved target MCP deployment extension.

EC2:
AWS Elastic Compute Cloud runtime host.

ECR:
AWS Elastic Container Registry used for Docker image storage.

SSM Parameter Store:
AWS secret/configuration storage direction for runtime secrets.

nginx:
Reverse proxy used in the documented AWS deployment path.

ChromaDB:
Vector-store technology used by the document and memory retrieval directions.

SPLADE:
Sparse retrieval technique used in the documented hybrid retrieval direction.

ColBERT:
Reranking/retrieval improvement direction. It shall not be assumed as implemented or superior without evaluation evidence.
<<<

[[/SECTION]]

[[SECTION]]
TITLE: 1.6 Ghost2 Future Vision Boundary

[TEXT]
STATEMENT: >>>
Ghost2 is a future product vision, not a completed current implementation.

The documented Ghost2 direction is a human-mediated multi-brain orchestration environment where private specialist AI contexts remain separate and selected knowledge can be synchronized into a shared GHOST board and shared memory layer.

A further Ghost2 direction is deterministic traceability across requirements, architecture, code, and tests. Stable IDs may connect related engineering artifacts. A lightweight SQLite-based traceability index is described as a possible practical knowledge-graph direction.

Ghost2 shall not be described as current product behavior unless it is explicitly promoted into approved requirements and supported by implementation-status evidence.
<<<

[[/SECTION]]

[[/SECTION]]

[[SECTION]]
TITLE: 2. Overall Description

[[SECTION]]
TITLE: 2.1 Product Perspective

[TEXT]
STATEMENT: >>>
GHOST is organized as a modular orchestration system. The main workflow connects user input, project knowledge, engineering memory, deterministic control logic, LLM-based agents, external AI tooling, and deployment infrastructure into one inspectable engineering process.

At the highest level, GHOST contains:

- a Streamlit GUI,
- an orchestration Controller,
- a SuperPrompt runtime state model,
- SuperPromptProjector prompt-ready rendering,
- a document knowledge pipeline,
- a configurable Agent Stack,
- project document stores,
- memory stores,
- structured logging direction,
- local development execution,
- current AWS deployment infrastructure,
- MCP interface infrastructure.

The architecture separates document ingestion and retrieval, memory recording and retrieval, prompt shaping and context construction, customizable agents, hard-rule direction, logging and observability, deployment, runtime persistence, and future traceability synchronization.
<<<

[[/SECTION]]

[[SECTION]]
TITLE: 2.2 Current Workflow and Pipeline Boundary

[TEXT]
STATEMENT: >>>
The documented conceptual workflow is:

GUI -> Controller -> Pipeline Stages -> SuperPrompt -> Prompt-ready output -> Optional external LLM or public AI platform

The conceptual target pipeline is:

A0_PreProcessing
A2_PromptShaper
Retrieval
ReRanker
A3_NLI_Gate
A4_Condenser
A5_Format_Enforcer
Prompt_Builder

The current executable GUI runner is more limited:

PreProcessing
A2
Retrieval
ReRanker or pass-through
A3
A4

The ActiveBrief relation classifier within the normal PreProcessing path, plus A2, A3, and A4, use the agent/LLM path where their execution conditions and configurations require it.

A5 is reserved/postponed and shall not be described as live behavior.

Prompt Builder is a target final assembly/send-boundary concept. Current GUI-visible rendered prompt output is owned by SuperPromptProjector and SuperPrompt prompt-ready composition.

The GHOST MCP interface provides a separate external tool boundary for approved AI clients. MCP may expose only capabilities explicitly approved in the 110-series requirement family. Common protocol behavior belongs to 110_mcp.sdoc, Prompt Engineering and Episodic/Clipboard/Collection Memory belong to 111_mcp_capabilities.sdoc, and all current and future ActiveBlackboard behavior belongs to 112_mcp_activeblackboard.sdoc.

The UI may present a visual macro-flow such as User Prompt, Prompt Qualification, Prompt Shaping, Memory Context, Document Evidence, Context Synthesis, Hard Rule Integration, and LLM Ready Context. This visual flow shall not be confused with the current backend executable runner.
<<<

[[/SECTION]]

[[SECTION]]
TITLE: 2.3 Authority and Evidence Order

[TEXT]
STATEMENT: >>>
The current user request and current task shall have highest authority in a run.

Memory, retrieved evidence, previous summaries, raw evidence, and historical context are supporting context only. They shall not override the current user request unless the user explicitly approves that interpretation.

The root SRS shall preserve this authority order because prompt construction, memory reuse, evidence selection, and future synchronization behavior depend on it.
<<<

[[/SECTION]]

[[SECTION]]
TITLE: 2.4 Core Data and Control Concepts

[TEXT]
STATEMENT: >>>
SuperPrompt is the authoritative in-memory state for the current run. It contains normalized prompt fields, stage state, retrieval views, selected chunk IDs, condensed context, memory context, attachments, diagnostics, and GUI-visible prompt-ready rendering.

The Controller owns the active SuperPrompt for a session, calls pipeline stages in legal order, updates stage/history fields, manages active project context, and avoids absorbing retrieval logic, embedding logic, LLM-provider logic, or GUI rendering responsibility.

Document stores and memory stores are controlled data domains.

Document ingestion produces chunks, stable IDs, metadata, embeddings, sparse representations where enabled, manifests, and persistent stores.

Memory recording produces durable MemoryRecords and metadata. Memory ingestion and retrieval work from durable memory truth without replacing it.

The memory truth split is:

- .ragmem stores stable memory body content,
- .ragmeta.json stores editable metadata mirror,
- SQLite stores query/index metadata.

Memory vectors, ActiveBriefs, compression outputs, and runtime MemoryContextPacks shall not replace durable memory truth.
<<<

[[/SECTION]]

[[SECTION]]
TITLE: 2.5 Capability Ownership Overview

[TEXT]
STATEMENT: >>>
GHOST is organized around the following approved capability ownership families:

- Orchestrator and Runtime Pipeline
- Agent Stack
- PreProcessing and Prompt Functions
- Knowledge Management
- Memory Management
- Human Workbench and Graphical Interfaces
- Runtime Platform and Operations
- Model Context Protocol
- Quality, Governance, and Observability
- Future Vision and Lifecycle Synchronization

The root SRS provides product-level requirement anchors for these capabilities. Detailed atomic requirements shall live in connected child StrictDoc files after human approval and evidence-based migration from legacy requirements, implementation status, architecture notes, UML files, and code.

The tree is capability-oriented. It shall not mechanically mirror the Python package tree, although implementation module names may be cited as evidence inside the owning child files.
<<<

[[/SECTION]]

[[SECTION]]
TITLE: 2.6 Current Baseline and Maturity Boundary

[TEXT]
STATEMENT: >>>
The current implementation baseline includes:

- Streamlit GUI structure,
- prompt input and engineered prompt display,
- current runner through A4,
- runtime log display,
- project selection,
- project-based ingestion controls,
- deterministic preprocessing,
- JSON-based Agent Stack,
- A2 PromptShaper,
- A3 usefulness gate,
- A4 condenser,
- SuperPrompt shared state,
- SuperPromptProjector prompt-ready rendering,
- project document ingestion,
- hybrid retrieval backbone,
- composite Retrieval stage with document retrieval and optional memory retrieval,
- document-only ReRanker behavior,
- documented current Streamlit AWS deployment,
- TextForge/RagLog logging direction,
- memory recording,
- memory ingestion,
- memory retrieval,
- server-side memory files,
- ChatGPT shared-link import,
- ActiveBrief relation classification,
- runtime MemoryMerge synthesis,
- implemented MCP server/tool infrastructure for Prompt Engineering, owner-scoped Direct Recall memory operations, and the Persistent Chat ActiveBlackboard prototype.

The following areas are incomplete, postponed, optional, placeholder, or future:

- dedicated final Prompt Builder/send-boundary,
- prompt_builder.py as complete final assembly authority,
- A5 Format Enforcer live controller action,
- full Hard Rules enforcement,
- Direct LLM Call as completed send-boundary,
- full observability/metrics dashboard,
- logger production hardening,
- multi-user support,
- Blackboard Actor persistence,
- automatic requirement-architecture-code synchronization,
- remaining unimplemented MCP memory behavior defined as TARGET in 111/112, including full intelligent Episodic retrieval, Clipboard Memory, Collection Memory, and future multi-actor ActiveBlackboard behavior,
- future React/TypeScript and FastAPI interface,
- ColBERT/reranking improvement as evaluated future topic.

The root SRS shall preserve the distinction between implemented behavior, documented design, planned near-term work, optional experiments, placeholders, and future vision.
<<<

[[/SECTION]]

[[SECTION]]
TITLE: 2.7 Assumptions and Dependencies

[TEXT]
STATEMENT: >>>
External model dependency:
GHOST currently depends on external LLM APIs for LLM-based stages such as A2, A3, A4, and future or optional LLM-assisted stages.

Public AI platform dependency:
GHOST may produce engineered prompts and selected context for use in public AI platforms. Those platforms are external to GHOST and are not controlled by GHOST.

Python package namespace:
The current Python implementation still uses the legacy package directory ragstream/. This is an implementation namespace and shall not change the product name.

Local runtime dependency:
GHOST currently depends on the local repository layout, project data directories, vector stores, and Python runtime environment during development execution.

AWS runtime dependency:
The documented AWS deployment, including the MCP deployment realization, depends on AWS infrastructure including EC2, ECR, Docker, nginx, HTTPS, Route53, SSM Parameter Store, and explicitly required persistent runtime data outside the Docker image.

Vector-store dependency:
Document and memory retrieval depend on ChromaDB and related vector-store assets where implemented.

Sparse-retrieval dependency:
SPLADE-based retrieval is part of the hybrid retrieval direction but shall remain optional and evaluation-dependent when practical tests do not show consistent improvement.

Document import dependency:
The current document upload/import boundary is limited to .txt and .md files unless later child requirements and implementation evidence extend it.

Human-control assumption:
The system assumes a human maintainer who approves requirement migration, source-of-truth cutover, synchronization decisions, memory reuse decisions, and future scope promotion.
<<<

[[/SECTION]]

[[SECTION]]
TITLE: 2.8 Requirement File Tree and Ownership Map

[TEXT]
STATEMENT: >>>
The following tree is the approved StrictDoc requirement ownership map for the current migration step.

Legend:

- [ROOT] root SRS and source-of-truth navigation
- [PARENT] parent child file with deeper child files
- [CHILD] detailed child requirement file
- [FUTURE] future/reserved capability, not current implementation truth
- [TARGET] approved required capability that is not yet implementation truth

Requirement File Tree::

  doc/01-Requirements/strictdoc/
  |-- 00_ghost_srs.sdoc                                  [ROOT]
  |   `-- Root SRS: product scope, naming, source-of-truth rules, current/future boundary, UID policy, and child-file map.
  |
  |-- 10_orchestrator_and_pipeline.sdoc                  [CHILD]
  |   `-- Controller role, SuperPrompt shared state, runtime pipeline sequencing, Prompt Builder runner, final prompt/send boundary, Direct LLM Call boundary, and subsystem coordination.
  |
  |-- 20_agent_stack.sdoc                                [CHILD]
  |   `-- JSON-based Agent Stack, AgentFactory, AgentPrompt, LLMClient, JSON configs, neutral/stateless infrastructure, and brief list of current agent users.
  |
  |-- 30_preprocessing_prompt_functions.sdoc             [CHILD]
  |   `-- A0 PreProcessing, prompt schema/header normalization, Prompt Qualifying / ActiveBrief Relation Classifier, A2 PromptShaper, A2 LLM bypass, and reserved Hard Rules fetch-copy behavior.
  |
  |-- 40_knowledge_management.sdoc                       [PARENT]
  |   |-- 41_document_ingestion.sdoc                     [CHILD]
  |   |-- 42_document_retrieval_and_reranking.sdoc       [CHILD]
  |   `-- 43_evidence_selection_and_condensation.sdoc    [CHILD]
  |
  |-- 50_memory_management.sdoc                          [PARENT]
  |   |-- 51_memory_recording_and_files.sdoc             [CHILD]
  |   |-- 52_memory_ingestion_and_retrieval.sdoc         [CHILD]
  |   `-- 53_memory_merge_activebrief_blackboard.sdoc    [CHILD/FUTURE-HOOKS]
  |
  |-- 60_context_integration_and_prompt_assembly.sdoc    [PARENT]
  |   |-- 61_superprompt_projection_and_prompt_builder.sdoc [CHILD]
  |   |-- 62_context_validation_deduplication_and_conflict_resolution.sdoc [CHILD/FUTURE]
  |   `-- 63_hard_rule_integration_and_finalization.sdoc [CHILD/FUTURE]
  |
  |-- 70_human_workbench_and_interfaces.sdoc             [PARENT]
  |   |-- 71_streamlit_workbench_current.sdoc            [CHILD]
  |   `-- 72_react_fastapi_interface_future.sdoc         [CHILD/FUTURE]
  |
  |-- 80_runtime_platform_and_operations.sdoc            [PARENT]
  |   `-- 81_aws_deployment_and_operations.sdoc          [CHILD]
  |       `-- Current AWS Streamlit deployment and target remote MCP deployment: Docker, EC2, ECR, nginx, HTTPS, Route53, SSM, persistence, activation, OAuth realization, and operational verification.
  |
  |-- 90_quality_governance_and_observability.sdoc       [PARENT]
  |   |-- 91_logging_textforge_raglog.sdoc               [CHILD]
  |   |-- 92_metrics_evaluation_benchmarking.sdoc        [CHILD/FUTURE]
  |   `-- 93_quality_security_traceability_governance.sdoc [CHILD]
  |
  |-- 100_future_vision_and_lifecycle_sync.sdoc           [FUTURE]
  |   `-- Requirement-Architecture-Code Sync reserved capability, Ghost2 boundary, advanced orchestration, and future capabilities not yet architecturally fixed.
  |
  `-- 110_mcp.sdoc                                      [PARENT]
      |-- 111_mcp_capabilities.sdoc                     [CHILD]
      `-- 112_mcp_activeblackboard.sdoc                 [CHILD/CURRENT+FUTURE]

Non-normative local operations profile:

doc-private/81_aws_deployment_profile.local.md records exact environment-specific values and implementation-assigned deployment values. It is not a StrictDoc child requirement file and shall not contain secret values.

Ownership rule:

The root SRS shall remain readable and navigable. It defines root anchors and ownership boundaries. Detailed atomic requirements shall be migrated into child files only after human approval.
<<<

[REQUIREMENT]
UID: GHOST-SRS-FILE-TREE
STATUS: Draft
TITLE: Requirement File Tree Parent Anchor
STATEMENT: >>>
This requirement is the parent anchor for the approved StrictDoc child-file tree. Connected child dummy files shall reference this UID, or a child-file parent UID, through StrictDoc parent references so generated HTML can display navigable requirement relationships.
<<<

[[/SECTION]]

[[/SECTION]]

[[SECTION]]
TITLE: 3. Specific Requirements

[[SECTION]]
TITLE: 3.1 Non-Functional Requirements

[[SECTION]]
TITLE: 3.1.1 Source of Truth, Authority, and Human Control

[TEXT]
STATEMENT: >>>
This section defines root governance policy directly in the root SRS. It has no separate child file in the first StrictDoc root version.
<<<

[REQUIREMENT]
UID: GHOST-SRS-NFR-SOT-001
STATUS: Draft
TITLE: Requirement Source of Truth During Migration
STATEMENT: >>>
Until explicit human-approved StrictDoc cutover, the approved existing requirement documents shall remain the requirement-level source of truth, while 00_ghost_srs.sdoc acts as the StrictDoc migration root and proposed future source-of-truth structure.
<<<

[REQUIREMENT]
UID: GHOST-SRS-NFR-SOT-002
STATUS: Draft
TITLE: Requirements Main Technical Authority
STATEMENT: >>>
Requirements_Main.md shall remain the main technical spine for subsystem boundaries, pipeline structure, SuperPrompt role, Controller role, Agent Stack role, ingestion and memory role, development phases, global design principles, and non-goals until StrictDoc child files replace it through approved cutover.
<<<

[REQUIREMENT]
UID: GHOST-SRS-NFR-SOT-003
STATUS: Draft
TITLE: README Product Identity Authority
STATEMENT: >>>
README.md shall remain the strongest source for GHOST product identity, motivation, public AI platform positioning, GHOST purpose, and Ghost2 vision wording until these concepts are explicitly migrated and approved in StrictDoc.
<<<

[REQUIREMENT]
UID: GHOST-SRS-NFR-SOT-004
STATUS: Draft
TITLE: Current User Request Priority
STATEMENT: >>>
The current user request and current task shall have higher authority than memory, retrieved evidence, previous summaries, raw evidence, and historical context during prompt construction and interpretation.
<<<

[REQUIREMENT]
UID: GHOST-SRS-NFR-SOT-005
STATUS: Draft
TITLE: Human Final Authority
STATEMENT: >>>
The human maintainer shall remain the final authority for requirement adoption, prioritization, interpretation, threshold approval, synchronization decisions, memory reuse decisions, model-bound context, and source-of-truth cutover.
<<<

[REQUIREMENT]
UID: GHOST-SRS-NFR-SOT-006
STATUS: Draft
TITLE: No Silent Behavioral Redefinition
STATEMENT: >>>
A new StrictDoc requirement shall not silently redefine stage behavior, controller behavior, ingestion behavior, retrieval behavior, memory behavior, GUI behavior, deployment behavior, or source-of-truth status already defined in approved project documents.
<<<

[[/SECTION]]

[[SECTION]]
TITLE: 3.1.2 Naming, Change Control, and Version Governance

[TEXT]
STATEMENT: >>>
This section applies the naming correction: the product is GHOST, and GHOST means GenAI Hybrid Orchestrator for Software Tooling.
<<<

[REQUIREMENT]
UID: GHOST-SRS-NFR-GOV-001
STATUS: Draft
TITLE: Product Name
STATEMENT: >>>
The product name in requirements, architecture, README-level product language, and stakeholder-facing documentation shall be GHOST.
<<<

[REQUIREMENT]
UID: GHOST-SRS-NFR-GOV-002
STATUS: Draft
TITLE: Product Acronym
STATEMENT: >>>
The acronym GHOST shall mean GenAI Hybrid Orchestrator for Software Tooling.
<<<

[REQUIREMENT]
UID: GHOST-SRS-NFR-GOV-003
STATUS: Draft
TITLE: Legacy Python Package Namespace
STATEMENT: >>>
The string ragstream shall be treated as the current legacy Python package directory name only. It shall not be used as the product identity in new requirement language.
<<<

[REQUIREMENT]
UID: GHOST-SRS-NFR-GOV-004
STATUS: Draft
TITLE: Legacy RAGstream Document Wording
STATEMENT: >>>
Existing pre-cutover documents may still use RAGstream as historical wording. New or migrated StrictDoc requirements shall use GHOST unless they explicitly describe legacy naming.
<<<

[REQUIREMENT]
UID: GHOST-SRS-NFR-GOV-005
STATUS: Draft
TITLE: Requirement Change Approval
STATEMENT: >>>
Changes to approved requirement meaning, UID policy, source-of-truth status, child-file ownership, or current/future classification shall require explicit human maintainer approval.
<<<

[REQUIREMENT]
UID: GHOST-SRS-NFR-GOV-006
STATUS: Draft
TITLE: Current Future Classification
STATEMENT: >>>
Each major capability shall remain clearly classified as implemented, documented design, planned, optional, postponed, placeholder, or future vision when that distinction is relevant to prevent scope confusion.
<<<

[[/SECTION]]

[[SECTION]]
TITLE: 3.1.3 UID and Traceability Policy

[TEXT]
STATEMENT: >>>
This section defines the minimal root UID and traceability policy required for the connected StrictDoc tree. Detailed governance and traceability requirements belong in 93_quality_security_traceability_governance.sdoc, while future lifecycle synchronization capability belongs in 100_future_vision_and_lifecycle_sync.sdoc.
<<<

[REQUIREMENT]
UID: GHOST-SRS-NFR-UID-001
STATUS: Draft
TITLE: Stable Requirement UIDs
STATEMENT: >>>
Requirement UIDs shall be treated as stable engineering addresses. Approved UIDs shall not be silently renamed, reused for different meaning, or renumbered only because files or implementation code move.
<<<

[REQUIREMENT]
UID: GHOST-SRS-NFR-UID-002
STATUS: Draft
TITLE: Root UID Prefixes
STATEMENT: >>>
The root SRS shall use GHOST-SRS-NFR for non-functional root requirements and GHOST-SRS-FR for functional root requirements. Child files shall use capability-specific UID prefixes aligned with the approved child-file map.
<<<

[REQUIREMENT]
UID: GHOST-SRS-NFR-UID-003
STATUS: Draft
TITLE: Capability-Oriented Requirement Tree
STATEMENT: >>>
The requirement tree shall be organized by functional capability and cross-cutting responsibility, not by mechanically mirroring the Python project tree.
<<<

[REQUIREMENT]
UID: GHOST-SRS-NFR-UID-004
STATUS: Draft
TITLE: Future Code UID Marker Direction
STATEMENT: >>>
The requirement system shall support the future direction that corresponding source-code units may carry requirement UID markers near relevant code so future audit or synchronization agents can compare requirements, architecture, code, and tests by stable IDs.
<<<

[REQUIREMENT]
UID: GHOST-SRS-NFR-UID-005
STATUS: Draft
TITLE: No Invented Synchronization Details
STATEMENT: >>>
The root SRS shall not define detailed implementation behavior for a future requirement-architecture-code synchronization agent beyond the agreed direction of stable IDs, artifact traceability, human approval, and possible future synchronization support.
<<<

[REQUIREMENT]
UID: GHOST-SRS-NFR-UID-006
STATUS: Draft
TITLE: Child File Linking Policy
STATEMENT: >>>
Child StrictDoc files shall be connected through stable parent anchor UIDs. Top-level child files shall reference GHOST-SRS-FILE-TREE, while deeper child files shall reference the root anchor UID of their approved parent child file.
<<<

[[/SECTION]]

[[SECTION]]
TITLE: 3.1.4 Quality, Governance, and Observability -> 90_quality_governance_and_observability.sdoc

[TEXT]
STATEMENT: >>>
Parent child file:

doc/01-Requirements/strictdoc/90_quality_governance_and_observability.sdoc

Deeper child files:

- doc/01-Requirements/strictdoc/91_logging_textforge_raglog.sdoc
- doc/01-Requirements/strictdoc/92_metrics_evaluation_benchmarking.sdoc
- doc/01-Requirements/strictdoc/93_quality_security_traceability_governance.sdoc

This area is a mixed FR/NFR cross-cutting ownership group. It shall contain functional logging requirements where logging is the subsystem behavior, and non-functional quality/governance requirements where logging, metrics, tests, security, or traceability serve validation and observability goals.
<<<

[REQUIREMENT]
UID: GHOST-SRS-NFR-QLT-001
STATUS: Draft
TITLE: Quality Governance Capability
STATEMENT: >>>
GHOST shall maintain cross-cutting quality governance for automated testing, structured logging, benchmarking and evaluation, security hardening, operational monitoring, source-of-truth governance, traceability rules, and requirement-change control.
<<<

[REQUIREMENT]
UID: GHOST-SRS-NFR-QLT-002
STATUS: Draft
TITLE: Measurable Targets To Be Defined
STATEMENT: >>>
Detailed child requirements shall later define measurable performance, reliability, usability, retrieval-quality, memory-quality, observability, and validation targets where evidence and stable implementation behavior are sufficient. This root SRS shall not invent unsupported numeric targets.
<<<

[REQUIREMENT]
UID: GHOST-SRS-NFR-QLT-003
STATUS: Draft
TITLE: Logging and Metrics Boundary
STATEMENT: >>>
GHOST shall distinguish the implemented TextForge/RagLog logging subsystem from future full operational metrics and observability behavior. Current Metrics UI behavior shall not be described as a completed observability dashboard unless supported by implementation evidence.
<<<

[[/SECTION]]

[[SECTION]]
TITLE: 3.1.5 Security, Privacy, and Operational Hardening -> 93_quality_security_traceability_governance.sdoc

[TEXT]
STATEMENT: >>>
Security and operational hardening are cross-cutting. Detailed security, privacy, source-of-truth, and traceability governance requirements belong in 93_quality_security_traceability_governance.sdoc. Runtime and deployment details connect to 80_runtime_platform_and_operations.sdoc.
<<<

[REQUIREMENT]
UID: GHOST-SRS-NFR-SEC-001
STATUS: Draft
TITLE: Security Hardening Direction
STATEMENT: >>>
GHOST shall support security hardening around secret discipline, backend exposure reduction, input-boundary hardening, dependency and image hygiene, security-relevant event logging, and operational verification checks.
<<<

[REQUIREMENT]
UID: GHOST-SRS-NFR-SEC-002
STATUS: Draft
TITLE: Context and Memory Control
STATEMENT: >>>
GHOST shall keep selected context, memory reuse, stored memory, excluded information, and model-bound information under explicit engineering control and human-visible inspection.
<<<

[[/SECTION]]

[[SECTION]]
TITLE: 3.1.6 Runtime Operations and Deployment -> 80_runtime_platform_and_operations.sdoc

[TEXT]
STATEMENT: >>>
Parent child file:

doc/01-Requirements/strictdoc/80_runtime_platform_and_operations.sdoc

Deeper child file:

doc/01-Requirements/strictdoc/81_aws_deployment_and_operations.sdoc

The runtime-platform branch shall own the documented AWS deployment realization, including MCP container execution, image delivery, HTTPS routing, DNS, runtime secrets, evidence-supported persistence, deployment activation, and operational verification. Functional MCP behavior shall remain owned by the 110-series MCP requirement family.

Exact environment-specific values belong in the non-normative local profile doc-private/81_aws_deployment_profile.local.md.
<<<

[REQUIREMENT]
UID: GHOST-SRS-NFR-OPS-001
STATUS: Draft
TITLE: Supported Runtime Contract Preservation
STATEMENT: >>>
Adopted capabilities shall preserve the explicitly specified functional and data contracts across their supported runtime environments.

This requirement shall not be interpreted as requiring identical directory layouts, storage mounts, process topology, or deployment infrastructure between local development execution and AWS deployment.
<<<

[REQUIREMENT]
UID: GHOST-SRS-NFR-OPS-002
STATUS: Draft
TITLE: Evidence-Bounded Persistent Runtime Data Separation
STATEMENT: >>>
Deployed runtime data that is explicitly required to survive container replacement shall remain outside the Docker image as defined by the owning deployment requirements.

Current persistence claims shall not exceed the evidence-supported bind mounts and paths documented by 81_aws_deployment_and_operations.sdoc. Additional target persistence shall require an explicit approved requirement.
<<<

[REQUIREMENT]
UID: GHOST-SRS-NFR-OPS-003
STATUS: Draft
TITLE: AWS Deployment Components
STATEMENT: >>>
The current Streamlit AWS deployment and the MCP deployment realization shall remain compatible with the approved Docker, ECR, EC2, nginx, HTTPS, Route53, SSM Parameter Store, and evidence-bounded persistence architecture defined by the owning deployment requirements.
<<<

[[/SECTION]]

[[SECTION]]
TITLE: 3.1.7 System Integrity and Failure Behavior

[TEXT]
STATEMENT: >>>
This section has no separate child file in the first root SRS. Detailed subsystem-specific failure behavior remains owned by the relevant child files.
<<<

[REQUIREMENT]
UID: GHOST-SRS-NFR-INT-001
STATUS: Draft
TITLE: SuperPrompt Runtime Truth
STATEMENT: >>>
SuperPrompt shall remain the authoritative in-memory state for the current run. No other runtime object shall keep a parallel source of truth for the active prompt, selected context, memory context, stage state, or prompt-ready rendering.
<<<

[REQUIREMENT]
UID: GHOST-SRS-NFR-INT-002
STATUS: Draft
TITLE: Stage Failure Integrity
STATEMENT: >>>
Stage failures shall not partially corrupt SuperPrompt state. Either a stage update is applied coherently, or the previous valid state remains available for inspection and recovery.
<<<

[REQUIREMENT]
UID: GHOST-SRS-NFR-INT-003
STATUS: Draft
TITLE: Inspectable Context Selection
STATEMENT: >>>
Selected document context, selected memory context, stage views, final selection IDs, condensed context, and model-bound context shall remain inspectable rather than hidden inside model calls.
<<<

[REQUIREMENT]
UID: GHOST-SRS-NFR-INT-004
STATUS: Draft
TITLE: No Silent Deletions
STATEMENT: >>>
Documents, memory entries, vectors, histories, and selected context shall not be silently deleted or ignored except through explicit user control, file-change logic, or approved retention policy.
<<<

[[/SECTION]]

[[SECTION]]
TITLE: 3.1.8 Non-Goals and Current Boundaries

[TEXT]
STATEMENT: >>>
This section preserves explicit current non-goals so future child files do not accidentally promote them into active scope.
<<<

[REQUIREMENT]
UID: GHOST-SRS-NFR-NG-001
STATUS: Draft
TITLE: No Current Dynamic Multi-Agent Planner Goal
STATEMENT: >>>
The current requirements shall not define a full multi-agent planner that dynamically rewires the pipeline as a current goal.
<<<

[REQUIREMENT]
UID: GHOST-SRS-NFR-NG-002
STATUS: Draft
TITLE: No Full LangChain or LangGraph Replacement Goal
STATEMENT: >>>
The current requirements shall not define GHOST as a full-blown LangChain or LangGraph replacement. The documented direction is a custom tight architecture that may borrow good ideas without replacing its own design.
<<<

[REQUIREMENT]
UID: GHOST-SRS-NFR-NG-003
STATUS: Draft
TITLE: No Current Multi-Tenant Policy Engine Goal
STATEMENT: >>>
The current requirements shall not define complex policy engines for access control, user management, or multi-tenant cloud deployment as current scope.
<<<

[REQUIREMENT]
UID: GHOST-SRS-NFR-NG-004
STATUS: Draft
TITLE: No Reinforcement Self-Tuning Goal
STATEMENT: >>>
The current requirements shall not define automatic self-tuning of pipeline parameters through reinforcement learning as current scope.
<<<

[[/SECTION]]

[[/SECTION]]

[[SECTION]]
TITLE: 3.2 Functional Requirements

[[SECTION]]
TITLE: 3.2.1 Orchestrator and Runtime Pipeline -> 10_orchestrator_and_pipeline.sdoc

[TEXT]
STATEMENT: >>>
Child file:

doc/01-Requirements/strictdoc/10_orchestrator_and_pipeline.sdoc

This file shall contain detailed requirements for Controller role, SuperPrompt shared state, runtime pipeline sequencing, Prompt Builder runner, final prompt/send boundary, Direct LLM Call boundary, manual memory-feed trigger points, and coordination of preprocessing, knowledge retrieval, memory retrieval, Agent Stack users, UI actions, and data-root coordination without data ownership.
<<<

[REQUIREMENT]
UID: GHOST-SRS-FR-ORCH-001
STATUS: Draft
TITLE: Orchestrator and Runtime Pipeline Capability
STATEMENT: >>>
GHOST shall provide a runtime orchestration spine that coordinates the active SuperPrompt, legal pipeline stage order, implemented stage calls, current GUI runner behavior, and final prompt/send-boundary direction without duplicating the internal ownership of preprocessing, knowledge, memory, agent, UI, logging, or runtime-platform subsystems.
<<<

[REQUIREMENT]
UID: GHOST-SRS-FR-ORCH-002
STATUS: Draft
TITLE: Current Executable Runner Boundary
STATEMENT: >>>
The current executable GUI runner shall be described as running through PreProcessing, A2, Retrieval, ReRanker or pass-through, A3, and A4, not as a completed full A0-to-Prompt-Builder target pipeline.
<<<

[REQUIREMENT]
UID: GHOST-SRS-FR-ORCH-003
STATUS: Draft
TITLE: SuperPrompt Runtime Truth
STATEMENT: >>>
The active SuperPrompt shall be treated as the session runtime truth for pipeline state, stage/history fields, retrieval state, memory context state, and prompt-ready rendering state.
<<<

[REQUIREMENT]
UID: GHOST-SRS-FR-ORCH-004
STATUS: Draft
TITLE: Final Prompt and Send Boundary
STATEMENT: >>>
The dedicated final Prompt Builder/send-boundary and Direct LLM Call behavior shall remain incomplete or boundary-level behavior until detailed child requirements and code evidence define them as completed product behavior.
<<<

[[/SECTION]]

[[SECTION]]
TITLE: 3.2.2 Agent Stack -> 20_agent_stack.sdoc

[TEXT]
STATEMENT: >>>
Child file:

doc/01-Requirements/strictdoc/20_agent_stack.sdoc

This file shall contain detailed requirements for AgentFactory, AgentPrompt, LLMClient, JSON agent configs, config loading/caching, neutral/stateless infrastructure, current JSON-based LLM-agent pattern, and the boundary between generic Agent Stack infrastructure and owning functional modules.
<<<

[REQUIREMENT]
UID: GHOST-SRS-FR-AGT-001
STATUS: Draft
TITLE: JSON-Based Agent Stack
STATEMENT: >>>
GHOST shall provide a neutral JSON-based Agent Stack consisting of AgentFactory, AgentPrompt, and LLMClient abstractions for implemented LLM-based stages and future specialist agents.
<<<

[REQUIREMENT]
UID: GHOST-SRS-FR-AGT-002
STATUS: Draft
TITLE: Current Agent Users
STATEMENT: >>>
The root SRS shall describe A2 PromptShaper, A3 NLI Gate, A4 Condenser, and ActiveBrief Relation Classifier as current users of the Agent Stack at a summary level. Detailed behavior shall remain in the owning functional child files.
<<<

[REQUIREMENT]
UID: GHOST-SRS-FR-AGT-003
STATUS: Draft
TITLE: LLM Client Boundary
STATEMENT: >>>
LLM-based stages shall access external model providers through the LLMClient abstraction rather than direct provider calls from Controller or GUI code, unless a future custom Python LLM-call path is explicitly approved and documented.
<<<

[[/SECTION]]

[[SECTION]]
TITLE: 3.2.3 PreProcessing and Prompt Functions -> 30_preprocessing_prompt_functions.sdoc

[TEXT]
STATEMENT: >>>
Child file:

doc/01-Requirements/strictdoc/30_preprocessing_prompt_functions.sdoc

This file shall contain detailed requirements for A0 deterministic PreProcessing, prompt schema/header normalization, MUST/default handling, baseline prompt_ready generation, Prompt Qualifying / ActiveBrief Relation Classifier, A2 PromptShaper, A2 LLM bypass behavior, and reserved/future Hard Rules deterministic fetch-copy behavior.
<<<

[REQUIREMENT]
UID: GHOST-SRS-FR-PRM-001
STATUS: Draft
TITLE: PreProcessing and Prompt Function Capability
STATEMENT: >>>
GHOST shall provide prompt-function behavior that normalizes user input, applies prompt schema/header handling, produces early relation signals where implemented, and shapes prompt metadata needed by downstream pipeline stages.
<<<

[REQUIREMENT]
UID: GHOST-SRS-FR-PRM-002
STATUS: Draft
TITLE: A2 PromptShaper Capability
STATEMENT: >>>
GHOST shall provide A2 PromptShaper behavior for selecting system, audience, tone, depth, confidence, and related prompt-shaping fields, including deterministic/default continuation when A2 LLM usage is bypassed.
<<<

[REQUIREMENT]
UID: GHOST-SRS-FR-PRM-003
STATUS: Draft
TITLE: ActiveBrief Relation Classifier Boundary
STATEMENT: >>>
GHOST shall preserve ActiveBrief relation classification as a PreProcessing-adjacent prompt function that produces prompt_materiality and topic_relation outputs. Detailed memory-lifecycle behavior belongs in Memory Management child files.
<<<

[REQUIREMENT]
UID: GHOST-SRS-FR-PRM-004
STATUS: Draft
TITLE: Hard Rules Boundary
STATEMENT: >>>
Full Hard Rules behavior shall remain reserved, postponed, or placeholder behavior until its final deterministic fetch-copy semantics, UI behavior, and final prompt insertion policy are approved in detailed requirements.
<<<

[[/SECTION]]

[[SECTION]]
TITLE: 3.2.4 Knowledge Management -> 40_knowledge_management.sdoc

[TEXT]
STATEMENT: >>>
Parent child file:

doc/01-Requirements/strictdoc/40_knowledge_management.sdoc

Deeper child files:

- doc/01-Requirements/strictdoc/41_document_ingestion.sdoc
- doc/01-Requirements/strictdoc/42_document_retrieval_and_reranking.sdoc
- doc/01-Requirements/strictdoc/43_evidence_selection_and_condensation.sdoc

The root SRS only states the main elements of project/document knowledge. Detailed ingestion, retrieval, reranking, A3, and A4 requirements belong in those child files.
<<<

[REQUIREMENT]
UID: GHOST-SRS-FR-KNOW-001
STATUS: Draft
TITLE: Knowledge Management Capability
STATEMENT: >>>
GHOST shall provide project document knowledge through project-scoped document ingestion, chunking, embeddings, sparse representations where enabled, vector stores, retrieval, document-only reranking, evidence filtering, and document evidence condensation.
<<<

[REQUIREMENT]
UID: GHOST-SRS-FR-KNOW-002
STATUS: Draft
TITLE: Document Import Boundary
STATEMENT: >>>
The current document upload/import boundary shall be described as limited to .txt and .md files unless later requirements and implementation evidence extend supported file types.
<<<

[REQUIREMENT]
UID: GHOST-SRS-FR-KNOW-003
STATUS: Draft
TITLE: Hybrid Document Retrieval
STATEMENT: >>>
GHOST shall provide deterministic project-aware document retrieval that combines dense retrieval and SPLADE sparse scoring in the documented hybrid retrieval path where the sparse branch is enabled.
<<<

[REQUIREMENT]
UID: GHOST-SRS-FR-KNOW-004
STATUS: Draft
TITLE: Document-Only ReRanker Boundary
STATEMENT: >>>
The ReRanker shall be described as operating on document retrieval results. Memory candidates shall remain separately represented in SuperPrompt and shall not be implied as part of the same reranked document candidate list.
<<<

[REQUIREMENT]
UID: GHOST-SRS-FR-KNOW-005
STATUS: Draft
TITLE: Evidence Selection and Condensation
STATEMENT: >>>
GHOST shall provide document evidence selection and condensation through ReRanker, A3 usefulness gating, A4 document-context condensation, final selection IDs, and GUI-inspectable stage views.
<<<

[[/SECTION]]

[[SECTION]]
TITLE: 3.2.5 Memory Management -> 50_memory_management.sdoc

[TEXT]
STATEMENT: >>>
Parent child file:

doc/01-Requirements/strictdoc/50_memory_management.sdoc

Deeper child files:

- doc/01-Requirements/strictdoc/51_memory_recording_and_files.sdoc
- doc/01-Requirements/strictdoc/52_memory_ingestion_and_retrieval.sdoc
- doc/01-Requirements/strictdoc/53_memory_merge_activebrief_blackboard.sdoc

Memory is intentionally split into durable recording/files, ingestion/retrieval, and runtime merge/ActiveBrief/future Blackboard hooks because the project separates durable memory truth from runtime memory context.
<<<

[REQUIREMENT]
UID: GHOST-SRS-FR-MEM-001
STATUS: Draft
TITLE: Memory Management Capability
STATEMENT: >>>
GHOST shall provide a structured engineering memory system for durable memory records, metadata, indexing, vector ingestion, retrieval, compression, merge, ActiveBrief direction, and controlled reuse of prior engineering context.
<<<

[REQUIREMENT]
UID: GHOST-SRS-FR-MEM-002
STATUS: Draft
TITLE: Memory Truth Split
STATEMENT: >>>
The memory system shall preserve the split between .ragmem stable memory body, .ragmeta.json editable metadata mirror, and SQLite query/index metadata.
<<<

[REQUIREMENT]
UID: GHOST-SRS-FR-MEM-003
STATUS: Draft
TITLE: Composite Retrieval Stage
STATEMENT: >>>
The current Retrieval stage shall be described as composite: document retrieval runs through the document path, and memory retrieval runs when MemoryRetriever is configured. Memory candidates shall remain separate from document candidates.
<<<

[REQUIREMENT]
UID: GHOST-SRS-FR-MEM-004
STATUS: Draft
TITLE: Memory Merge and Open Final Policy
STATEMENT: >>>
Memory retrieval, runtime compression, and MemoryMerge synthesis exist, but final Direct Recall priority, memory-context inclusion policy, and final Prompt Builder/send-boundary behavior remain open until approved child requirements define them.
<<<

[REQUIREMENT]
UID: GHOST-SRS-FR-MEM-005
STATUS: Draft
TITLE: ActiveRetrievalBrief and Blackboard Boundary
STATEMENT: >>>
GHOST shall preserve ActiveRetrievalBrief as part of the memory-management direction, while Blackboard memory hooks shall remain future/reserved unless later requirements and implementation evidence define durable product behavior.
<<<

[[/SECTION]]

[[SECTION]]
TITLE: 3.2.6 Human Workbench and Graphical Interfaces -> 70_human_workbench_and_interfaces.sdoc

[TEXT]
STATEMENT: >>>
Parent child file:

doc/01-Requirements/strictdoc/70_human_workbench_and_interfaces.sdoc

Deeper child files:

- doc/01-Requirements/strictdoc/71_streamlit_workbench_current.sdoc
- doc/01-Requirements/strictdoc/72_react_fastapi_interface_future.sdoc

This area owns the human-facing graphical interface family consisting of the current Streamlit workbench and the future React/TypeScript and FastAPI interface. MCP is a separate 110-series capability family.
<<<

[REQUIREMENT]
UID: GHOST-SRS-FR-UI-001
STATUS: Draft
TITLE: Human Workbench Capability
STATEMENT: >>>
GHOST shall provide a human-facing workbench for prompt input, project selection, ingestion controls, pipeline execution, engineered prompt display, memory controls, runtime logging, file management, and inspection of system state.
<<<

[REQUIREMENT]
UID: GHOST-SRS-FR-UI-002
STATUS: Draft
TITLE: Streamlit Current Interface Boundary
STATEMENT: >>>
The current implemented user interface shall be described as Streamlit-based and shall include only features supported by current implementation evidence or approved child requirements.
<<<

[REQUIREMENT]
UID: GHOST-SRS-FR-UI-003
STATUS: Draft
TITLE: React/FastAPI Future Interface Boundary
STATEMENT: >>>
React/TypeScript frontend and FastAPI backend architecture shall be treated as future interface direction until detailed requirements and implementation evidence define it as current behavior.
<<<

[REQUIREMENT]
UID: GHOST-SRS-FR-UI-004
STATUS: Draft
TITLE: GUI Placeholder Boundary
STATEMENT: >>>
GUI elements for Hard Rules, Direct LLM Call, metrics/observability, prompt-only mode, Blackboard Actor, or future behavior shall not be described as completed product behavior unless supported by implementation evidence and approved child requirements.
<<<

[[/SECTION]]

[[SECTION]]
TITLE: 3.2.7 External Interfaces and AI Tooling Boundary

[TEXT]
STATEMENT: >>>
This section gives only root-level external-interface categories. Detailed MCP protocol and common behavior belong to 110_mcp.sdoc; Prompt Engineering and Episodic/Clipboard/Collection Memory belong to 111_mcp_capabilities.sdoc; ActiveBlackboard belongs to 112_mcp_activeblackboard.sdoc; concrete AWS deployment realization remains owned by 81_aws_deployment_and_operations.sdoc.
<<<

[REQUIREMENT]
UID: GHOST-SRS-FR-EXT-001
STATUS: Draft
TITLE: External AI Tooling Compatibility
STATEMENT: >>>
GHOST shall support workflows where engineered prompts and selected context can be used with external AI tooling while keeping surrounding context construction, memory, rules direction, retrieval, and synchronization direction under GHOST control.
<<<

[REQUIREMENT]
UID: GHOST-SRS-FR-EXT-006
STATUS: Draft
TITLE: MCP External Interface Capability
STATEMENT: >>>
GHOST shall provide an MCP interface through which approved ChatGPT and Claude clients can invoke explicitly exposed GHOST capabilities.

Common MCP protocol, transport, authorization, owner-isolation, error, and interoperability requirements shall remain owned by 110_mcp.sdoc. Prompt Engineering and non-ActiveBlackboard memory requirements shall remain owned by 111_mcp_capabilities.sdoc. All current and future ActiveBlackboard requirements shall remain owned by 112_mcp_activeblackboard.sdoc. Concrete AWS deployment realization shall remain owned by 81_aws_deployment_and_operations.sdoc.
<<<

[REQUIREMENT]
UID: GHOST-SRS-FR-EXT-002
STATUS: Draft
TITLE: Direct LLM Call Boundary
STATEMENT: >>>
Direct LLM Call shall be treated as optional future send-boundary behavior or placeholder behavior until current code evidence and approved child requirements define it as completed.
<<<

[REQUIREMENT]
UID: GHOST-SRS-FR-EXT-003
STATUS: Draft
TITLE: Browser User Interface Boundary
STATEMENT: >>>
The current GHOST user interface shall be accessed as a browser-based Streamlit application in local and deployed runtime modes.
<<<

[REQUIREMENT]
UID: GHOST-SRS-FR-EXT-004
STATUS: Draft
TITLE: Runtime Network Boundary
STATEMENT: >>>
The deployed Streamlit GUI and the remote MCP interface shall be exposed through their documented AWS reverse-proxy and HTTPS paths rather than treating internal application or container ports as public product interfaces.
<<<

[REQUIREMENT]
UID: GHOST-SRS-FR-EXT-005
STATUS: Draft
TITLE: File System Interface Boundary
STATEMENT: >>>
GHOST shall use documented project data directories and runtime data directories as controlled file-system interfaces for project documents, vector stores, memory files, manifests, logs, and persistent runtime data.
<<<

[[/SECTION]]

[[SECTION]]
TITLE: 3.2.8 Runtime Platform and Operations -> 80_runtime_platform_and_operations.sdoc

[TEXT]
STATEMENT: >>>
Parent child file:

doc/01-Requirements/strictdoc/80_runtime_platform_and_operations.sdoc

Deeper child file:

doc/01-Requirements/strictdoc/81_aws_deployment_and_operations.sdoc

This branch shall contain the functional and non-functional runtime and deployment requirements for the documented AWS deployment, including the MCP deployment realization. Functional MCP tool behavior remains outside this branch in the 110-series requirements. Exact environment-specific values shall remain in the non-normative local profile doc-private/81_aws_deployment_profile.local.md.
<<<

[REQUIREMENT]
UID: GHOST-SRS-FR-RUN-001
STATUS: Draft
TITLE: Runtime Platform and Operations Capability
STATEMENT: >>>
GHOST shall support the documented AWS Streamlit and MCP deployment realization through the runtime and operations contracts defined by 80_runtime_platform_and_operations.sdoc and 81_aws_deployment_and_operations.sdoc.
<<<

[REQUIREMENT]
UID: GHOST-SRS-FR-RUN-002
STATUS: Draft
TITLE: Runtime Persistence Capability
STATEMENT: >>>
The Streamlit deployment shall preserve the evidence-supported raw-document and Chroma-database data through external bind mounts across Streamlit container replacement.

The MCP deployment shall additionally preserve MCP memory data when required by the approved 111/112 memory capabilities and the owning deployment requirements. Other runtime artifacts shall not be claimed as persistent without an owning requirement and deployment realization.
<<<

[REQUIREMENT]
UID: GHOST-SRS-FR-RUN-003
STATUS: Draft
TITLE: Single-User Private Instance Boundary
STATEMENT: >>>
The current deployed runtime shall be described as private-instance and single-user/single-workspace unless later requirements and implementation evidence define multi-user SaaS behavior.
<<<

[[/SECTION]]

[[SECTION]]
TITLE: 3.2.9 Quality, Governance, and Observability -> 90_quality_governance_and_observability.sdoc

[TEXT]
STATEMENT: >>>
Parent child file:

doc/01-Requirements/strictdoc/90_quality_governance_and_observability.sdoc

Deeper child files:

- doc/01-Requirements/strictdoc/91_logging_textforge_raglog.sdoc
- doc/01-Requirements/strictdoc/92_metrics_evaluation_benchmarking.sdoc
- doc/01-Requirements/strictdoc/93_quality_security_traceability_governance.sdoc

This area is cross-cutting and may contain both functional subsystem requirements, such as logging, and non-functional quality/governance requirements.
<<<

[REQUIREMENT]
UID: GHOST-SRS-FR-QGO-001
STATUS: Draft
TITLE: Cross-Cutting Quality and Observability Capability
STATEMENT: >>>
GHOST shall preserve a cross-cutting requirement area for implemented logging behavior, future metrics/evaluation behavior, testing, security hardening, source-of-truth governance, change control, and traceability rules.
<<<

[REQUIREMENT]
UID: GHOST-SRS-FR-QGO-002
STATUS: Draft
TITLE: Functional Logging Subsystem Boundary
STATEMENT: >>>
TextForge/RagLog shall be treated as a functional logging subsystem whose detailed behavior belongs in 91_logging_textforge_raglog.sdoc.
<<<

[REQUIREMENT]
UID: GHOST-SRS-FR-QGO-003
STATUS: Draft
TITLE: Metrics and Evaluation Boundary
STATEMENT: >>>
Metrics, evaluation, benchmarking, token/cost/latency tracking, retrieval counts, memory diagnostics, and quality regression checks shall be treated as future or partially implemented observability/evaluation requirements unless supported by implementation evidence.
<<<

[[/SECTION]]

[[SECTION]]
TITLE: 3.2.10 Future Vision and Lifecycle Synchronization -> 100_future_vision_and_lifecycle_sync.sdoc

[TEXT]
STATEMENT: >>>
Child file:

doc/01-Requirements/strictdoc/100_future_vision_and_lifecycle_sync.sdoc

This file shall contain Requirement-Architecture-Code Sync reserved capability, the broader Ghost2 future boundary, advanced orchestration, future model/backend expansion, and other future capabilities not yet architecturally fixed. Detailed MCP ActiveBlackboard requirements are owned by 112_mcp_activeblackboard.sdoc.
<<<

[REQUIREMENT]
UID: GHOST-SRS-FR-FUT-001
STATUS: Draft
TITLE: Future Capability Isolation
STATEMENT: >>>
GHOST shall keep future ideas and backlog features isolated from active behavior unless the human maintainer explicitly promotes them into approved requirements.
<<<

[REQUIREMENT]
UID: GHOST-SRS-FR-FUT-002
STATUS: Draft
TITLE: Requirement-Architecture-Code Sync Boundary
STATEMENT: >>>
GHOST shall preserve a future capability direction for deterministic traceability and synchronization across requirements, architecture, code, and tests using stable IDs, while avoiding claims that this behavior is currently implemented.
<<<

[REQUIREMENT]
UID: GHOST-SRS-FR-FUT-003
STATUS: Draft
TITLE: Ghost2 Future Boundary
STATEMENT: >>>
GHOST shall keep Ghost2 as a future capability direction for human-mediated multi-brain orchestration, private specialist contexts, shared board behavior, shared memory, and traceability-assisted collaboration until promoted into active child requirements.
<<<

[REQUIREMENT]
UID: GHOST-SRS-FR-FUT-004
STATUS: Draft
TITLE: Blackboard Actor Boundary
STATEMENT: >>>
The Blackboard Actor selector shall be treated as a demo or future UI concept unless later evidence and requirements define it as durable persisted product functionality.
<<<

[[/SECTION]]

[[/SECTION]]

[[/SECTION]]

[DOCUMENT]
TITLE: GHOST Preprocessing and Prompt Functions Requirements
UID: GHOST-PREPROCESSING-PROMPT-FUNCTIONS
VERSION: 0.1
OPTIONS:
  MARKUP: Text
  AUTO_LEVELS: On
  NODE_IN_TOC: True

[[SECTION]]
TITLE: 1. Purpose and Scope

[TEXT]
STATEMENT: >>>
This document defines the requirements for the GHOST prompt-preparation capability from receipt of raw user text until the prepared SuperPrompt is handed to the Knowledge Management and Memory Management retrieval paths.

The capability has three major functional parts:
1. deterministic prompt parsing, canonical field mapping, mandatory-field handling, and initial SuperPrompt construction;
2. ActiveBrief-aware prompt materiality and topic-relation classification followed by deterministic routing policy;
3. A2 PromptShaper classification of system, audience, tone, depth, confidence, and evidence policy.

This document defines requirements. It does not serve as an implementation-status report.
<<<

[REQUIREMENT]
UID: GHOST-PREPROCESS-ROOT
STATUS: Draft
TITLE: Preprocessing and Prompt Functions Scope
STATEMENT: >>>
GHOST shall provide one prompt-preparation capability that transforms raw user input into a structured and routed SuperPrompt ready for downstream Knowledge Management and Memory Management processing.

The capability shall include deterministic preprocessing, ActiveBrief relation classification, deterministic routing decisions, A2 PromptShaper execution, synchronized retrieval-query construction, and final prompt-preview projection.

The capability shall stop at the handoff boundary and shall not execute document retrieval, memory retrieval, document reranking, evidence selection, evidence condensation, or memory-context synthesis.
<<<
RELATIONS:
- TYPE: Parent
  VALUE: GHOST-SRS-FILE-TREE

[REQUIREMENT]
UID: GHOST-PREPROCESS-PRODUCT-NAME
STATUS: Draft
TITLE: Product and Package Naming Boundary
STATEMENT: >>>
The product described by this document shall be named GHOST.

The existing Python package namespace may remain ragstream in current source code and implementation paths.

Requirements shall not treat ragstream as the product identity.
<<<
RELATIONS:
- TYPE: Parent
  VALUE: GHOST-PREPROCESS-ROOT

[REQUIREMENT]
UID: GHOST-PREPROCESS-THREE-PART-MODEL
STATUS: Draft
TITLE: Three-Part Prompt-Preparation Model
STATEMENT: >>>
The GHOST prompt-preparation capability shall be organized into these three functional parts:

1. Deterministic Prompt Structuring.
2. ActiveBrief Relation Classification and Routing.
3. A2 PromptShaper and Job Structuring.

Each part shall have explicit inputs, outputs, responsibility boundaries, and acceptance criteria.
<<<
RELATIONS:
- TYPE: Parent
  VALUE: GHOST-PREPROCESS-ROOT

[REQUIREMENT]
UID: GHOST-PREPROCESS-CURRENT-SCOPE
STATUS: Draft
TITLE: Current Executable Scope
STATEMENT: >>>
The current executable scope shall include:
- schema-driven deterministic header parsing and name resolution;
- TASK and CONTEXT fallback behavior;
- default handling for active mandatory fields;
- SuperPrompt body and lifecycle updates;
- ActiveBrief discovery and snapshotting;
- two-dimensional LLM classification of prompt materiality and topic relation;
- deterministic routing policy derived from the classifier result;
- A2 selector execution or deterministic-default mode;
- synchronized effective retrieval-query creation;
- central SuperPrompt projection for the prepared prompt preview.

Unimplemented semantic header matching, fuzzy matching, future A2 passes, and downstream retrieval algorithms shall not be presented as current behavior.
<<<
RELATIONS:
- TYPE: Parent
  VALUE: GHOST-PREPROCESS-ROOT

[[/SECTION]]

[[SECTION]]
TITLE: 2. Functional Architecture and Responsibility Boundaries

[TEXT]
STATEMENT: >>>
The prompt-preparation path combines deterministic processing and narrowly bounded LLM classification.

The high-level flow is:

raw user text
-> deterministic parsing and canonicalization
-> initial SuperPrompt update
-> ActiveBrief relation classification
-> deterministic six-state routing policy
-> synchronized retrieval-query projection
-> A2 PromptShaper
-> prepared handoff to Knowledge and Memory Retrieval
<<<

[REQUIREMENT]
UID: GHOST-PREPROCESS-END-TO-END-FLOW
STATUS: Draft
TITLE: Raw-Input-to-Retrieval-Handoff Flow
STATEMENT: >>>
The prompt-preparation capability shall accept raw user text and shall produce a SuperPrompt whose current request, meta-configuration, ActiveBrief routing metadata, effective retrieval query, lifecycle state, and prompt preview are ready for downstream context generation.

The output of this capability shall be the authoritative prepared runtime state for the current request.
<<<
RELATIONS:
- TYPE: Parent
  VALUE: GHOST-PREPROCESS-ROOT

[REQUIREMENT]
UID: GHOST-PREPROCESS-DETERMINISTIC-BOUNDARY
STATUS: Draft
TITLE: Deterministic Preprocessing Boundary
STATEMENT: >>>
Header parsing, key normalization, canonical-name matching, alias matching, bilingual matching, TASK/CONTEXT fallback, active mandatory-field defaulting, body write-back, and lifecycle bookkeeping shall be deterministic.

The deterministic preprocessing layer shall not call an LLM and shall not apply fuzzy, semantic, template, cue-based, or probabilistic header inference in the current runtime.
<<<
RELATIONS:
- TYPE: Parent
  VALUE: GHOST-PREPROCESS-END-TO-END-FLOW

[REQUIREMENT]
UID: GHOST-PREPROCESS-CLASSIFIER-BOUNDARY
STATUS: Draft
TITLE: ActiveBrief Classifier Boundary
STATEMENT: >>>
The ActiveBrief relation classifier shall decide only:
- prompt_materiality; and
- topic_relation.

It shall not decide document-retrieval actions, memory-context actions, final prompt-display actions, pipeline stage order, or downstream evidence behavior.

Those actions shall be determined by explicit deterministic Python policy.
<<<
RELATIONS:
- TYPE: Parent
  VALUE: GHOST-PREPROCESS-END-TO-END-FLOW

[REQUIREMENT]
UID: GHOST-PREPROCESS-A2-BOUNDARY
STATUS: Draft
TITLE: A2 PromptShaper Boundary
STATEMENT: >>>
A2 PromptShaper shall classify configured prompt meta-fields from the already normalized current request.

A2 shall not parse raw Markdown headers, select an ActiveBrief, execute Knowledge Retrieval, execute Memory Retrieval, or own final answer generation.
<<<
RELATIONS:
- TYPE: Parent
  VALUE: GHOST-PREPROCESS-END-TO-END-FLOW

[REQUIREMENT]
UID: GHOST-PREPROCESS-AGENT-STACK-REFERENCE
STATUS: Draft
TITLE: Agent Stack Infrastructure Reference
STATEMENT: >>>
ActiveBrief relation classification and A2 PromptShaper shall use the neutral Agent Stack contracts defined in 20_agent_stack.sdoc.

This file shall own the functional meaning, runtime payload, deterministic validation, routing policy, and SuperPrompt write-back of these concrete prompt functions.

This file shall not duplicate the generic AgentFactory, AgentPrompt, or LLMClient infrastructure requirements.
<<<
RELATIONS:
- TYPE: Parent
  VALUE: GHOST-PREPROCESS-END-TO-END-FLOW

[REQUIREMENT]
UID: GHOST-PREPROCESS-SUPERPROMPT-BOUNDARY
STATUS: Draft
TITLE: SuperPrompt State Boundary
STATEMENT: >>>
SuperPrompt shall remain the authoritative shared runtime state for prompt preparation.

PromptSchema, NameMatcher, ActiveBrief classifier configuration, AgentPrompt, and LLMClient shall not become parallel owners of the current prepared prompt state.

All persistent prompt-preparation outcomes required by downstream stages shall be written explicitly into SuperPrompt body fields, lifecycle fields, or extras.
<<<
RELATIONS:
- TYPE: Parent
  VALUE: GHOST-PREPROCESS-END-TO-END-FLOW

[REQUIREMENT]
UID: GHOST-PREPROCESS-ORCHESTRATION-BOUNDARY
STATUS: Draft
TITLE: Controller Coordination Boundary
STATEMENT: >>>
The application controller shall coordinate deterministic preprocessing, ActiveBrief relation classification, central prompt projection, and A2 invocation.

The controller shall not absorb schema normalization rules, classifier semantics, A2 selector sanitization, or downstream retrieval algorithms.
<<<
RELATIONS:
- TYPE: Parent
  VALUE: GHOST-PREPROCESS-END-TO-END-FLOW

[REQUIREMENT]
UID: GHOST-PREPROCESS-KNOWLEDGE-BOUNDARY
STATUS: Draft
TITLE: Knowledge Management Boundary
STATEMENT: >>>
This file shall prepare the effective document-retrieval query and document-retrieval routing state.

Detailed document ingestion, dense retrieval, SPLADE retrieval, fusion, reranking, usefulness selection, and evidence condensation shall remain owned by the Knowledge Management requirement files.
<<<
RELATIONS:
- TYPE: Parent
  VALUE: GHOST-PREPROCESS-END-TO-END-FLOW

[REQUIREMENT]
UID: GHOST-PREPROCESS-MEMORY-BOUNDARY
STATUS: Draft
TITLE: Memory Management Boundary
STATEMENT: >>>
This file shall prepare the memory-context permission and ActiveBrief continuity state required by downstream memory processing.

Detailed memory recording, ActiveBrief creation and update, memory ingestion, memory retrieval, memory scoring, and memory-context synthesis shall remain owned by the Memory Management requirement files.
<<<
RELATIONS:
- TYPE: Parent
  VALUE: GHOST-PREPROCESS-END-TO-END-FLOW

[[/SECTION]]

[[SECTION]]
TITLE: 3. Prompt Schema and Canonical Field Contract

[TEXT]
STATEMENT: >>>
Deterministic preprocessing is driven by a prompt schema. The schema defines the recognized prompt vocabulary; SuperPrompt defines the active runtime field model.

Schema declarations and runtime fields shall remain explicitly mapped so that configured mandatory fields are not silently discarded.
<<<

[REQUIREMENT]
UID: GHOST-PREPROCESS-SCHEMA-LOAD
STATUS: Draft
TITLE: Prompt Schema Loading
STATEMENT: >>>
The controller shall load the prompt schema from a configured JSON path and shall make one reusable PromptSchema instance available to deterministic preprocessing.

The schema shall be loaded before prompt parsing begins.
<<<
RELATIONS:
- TYPE: Parent
  VALUE: GHOST-PREPROCESS-ROOT

[REQUIREMENT]
UID: GHOST-PREPROCESS-SCHEMA-JSON
STATUS: Draft
TITLE: Prompt Schema JSON Contract
STATEMENT: >>>
The current prompt schema shall be represented as a JSON object.

The executable deterministic preprocessing contract may use:
- canonical_keys;
- must_keys;
- defaults;
- aliases; and
- bilingual mappings.

Additional schema sections shall not be treated as active runtime behavior unless a current requirement and implementation consume them.
<<<
RELATIONS:
- TYPE: Parent
  VALUE: GHOST-PREPROCESS-SCHEMA-LOAD

[REQUIREMENT]
UID: GHOST-PREPROCESS-SCHEMA-NORMALIZATION
STATUS: Draft
TITLE: Header-Key Normalization
STATEMENT: >>>
Prompt header keys shall be normalized deterministically by:
1. accepting string input only;
2. applying Unicode NFKC normalization;
3. converting to lowercase;
4. trimming leading and trailing whitespace;
5. collapsing internal whitespace runs; and
6. removing punctuation from the header key used for matching.

Header-key normalization shall not modify the section body text.
<<<
RELATIONS:
- TYPE: Parent
  VALUE: GHOST-PREPROCESS-SCHEMA-LOAD

[REQUIREMENT]
UID: GHOST-PREPROCESS-RUNTIME-BODY-FIELDS
STATUS: Draft
TITLE: Current Runtime Prompt Body Fields
STATEMENT: >>>
The current SuperPrompt prompt-body contract shall support these runtime keys:
- system;
- task;
- audience;
- role;
- tone;
- depth;
- confidence;
- evidence_policy;
- context;
- purpose;
- format;
- text.

Prompt preprocessing shall write only to fields defined by the active SuperPrompt body contract.
<<<
RELATIONS:
- TYPE: Parent
  VALUE: GHOST-PREPROCESS-SCHEMA-LOAD

[REQUIREMENT]
UID: GHOST-PREPROCESS-SCHEMA-RUNTIME-MAPPING
STATUS: Draft
TITLE: Schema-to-Runtime Field Mapping
STATEMENT: >>>
Schema-facing canonical names shall have an explicit deterministic mapping to the active SuperPrompt runtime keys.

In particular:
- response_depth shall map to depth;
- output_format shall map to format.

A schema key shall not be considered successfully applied merely because it was recognized if no runtime destination receives its value.
<<<
RELATIONS:
- TYPE: Parent
  VALUE: GHOST-PREPROCESS-RUNTIME-BODY-FIELDS

[REQUIREMENT]
UID: GHOST-PREPROCESS-MUST-DESTINATION
STATUS: Draft
TITLE: Mandatory Field Runtime Destination
STATEMENT: >>>
Every active schema field declared mandatory shall have one defined runtime destination or shall be removed from the active mandatory-field set.

The system shall not silently claim enforcement of a mandatory schema field whose value is discarded before SuperPrompt write-back.
<<<
RELATIONS:
- TYPE: Parent
  VALUE: GHOST-PREPROCESS-SCHEMA-RUNTIME-MAPPING

[REQUIREMENT]
UID: GHOST-PREPROCESS-CANONICAL-MATCH
STATUS: Draft
TITLE: Canonical Header Match
STATEMENT: >>>
A normalized header matching an active canonical schema key shall resolve directly to that canonical key.
<<<
RELATIONS:
- TYPE: Parent
  VALUE: GHOST-PREPROCESS-SCHEMA-LOAD

[REQUIREMENT]
UID: GHOST-PREPROCESS-ALIAS-MATCH
STATUS: Draft
TITLE: Alias Header Match
STATEMENT: >>>
A normalized header not matched canonically may resolve through the configured alias map.

The alias target shall resolve to an active canonical key before runtime write-back.
<<<
RELATIONS:
- TYPE: Parent
  VALUE: GHOST-PREPROCESS-CANONICAL-MATCH

[REQUIREMENT]
UID: GHOST-PREPROCESS-BILINGUAL-MATCH
STATUS: Draft
TITLE: Bilingual Header Match
STATEMENT: >>>
A normalized header not matched canonically or through an alias may resolve through a configured bilingual mapping.

The current schema may provide German-to-canonical mappings without requiring language detection.
<<<
RELATIONS:
- TYPE: Parent
  VALUE: GHOST-PREPROCESS-ALIAS-MATCH

[REQUIREMENT]
UID: GHOST-PREPROCESS-MATCH-ORDER
STATUS: Draft
TITLE: Deterministic Name-Matching Order
STATEMENT: >>>
Header resolution shall use this fixed order:
1. canonical match;
2. alias match;
3. bilingual match;
4. unknown.

A lower-priority method shall not override a successful higher-priority match.
<<<
RELATIONS:
- TYPE: Parent
  VALUE: GHOST-PREPROCESS-BILINGUAL-MATCH

[REQUIREMENT]
UID: GHOST-PREPROCESS-NO-FUZZY-MATCHING
STATUS: Draft
TITLE: No Current Fuzzy or Semantic Matching
STATEMENT: >>>
The current deterministic header resolver shall not use edit distance, typo correction, templates, keyword cues, embeddings, LLM inference, or semantic similarity.

Schema data for such future behavior may exist without making that behavior part of the current executable requirement.
<<<
RELATIONS:
- TYPE: Parent
  VALUE: GHOST-PREPROCESS-MATCH-ORDER

[REQUIREMENT]
UID: GHOST-PREPROCESS-SCHEMA-VERSION
STATUS: Draft
TITLE: Prompt Schema Version Traceability
STATEMENT: >>>
The prompt schema shall expose a version identifier sufficient to trace the canonical field vocabulary used by a prompt-preparation baseline.

An approved change to canonical keys, mandatory fields, defaults, aliases, bilingual mappings, or schema-to-runtime mappings shall update the affected requirements and verification assets.
<<<
RELATIONS:
- TYPE: Parent
  VALUE: GHOST-PREPROCESS-SCHEMA-LOAD

[[/SECTION]]

[[SECTION]]
TITLE: 4. Deterministic Prompt Parsing and Name Resolution

[TEXT]
STATEMENT: >>>
The deterministic parser converts either Markdown-like structured input or unstructured plain text into recognized prompt sections.

The parser does not infer user intent beyond the explicit deterministic rules in this section.
<<<

[REQUIREMENT]
UID: GHOST-PREPROCESS-NONEMPTY-INPUT
STATUS: Draft
TITLE: Non-Empty Raw Input Processing
STATEMENT: >>>
The controller shall trim the raw user text before starting prompt preparation.

Whitespace-only input shall return the existing SuperPrompt without adding a preprocessing stage entry or invoking the ActiveBrief classifier.
<<<
RELATIONS:
- TYPE: Parent
  VALUE: GHOST-PREPROCESS-ROOT

[REQUIREMENT]
UID: GHOST-PREPROCESS-HEADER-LEVELS
STATUS: Draft
TITLE: Supported Header Levels
STATEMENT: >>>
Structured prompt parsing shall recognize headings beginning with one, two, or three hash characters.

Headings deeper than three levels shall not be treated as prompt-field headers by the current parser.
<<<
RELATIONS:
- TYPE: Parent
  VALUE: GHOST-PREPROCESS-NONEMPTY-INPUT

[REQUIREMENT]
UID: GHOST-PREPROCESS-HEADER-SYNTAX
STATUS: Draft
TITLE: Current Header Syntax
STATEMENT: >>>
A current prompt-field heading shall contain:
- one to three leading hash characters;
- optional whitespace after the hash characters; and
- a non-empty header title.

Therefore both "## TASK" and "##TASK" shall be interpreted according to the same current header-title matching rules.
<<<
RELATIONS:
- TYPE: Parent
  VALUE: GHOST-PREPROCESS-HEADER-LEVELS

[REQUIREMENT]
UID: GHOST-PREPROCESS-SECTION-BOUNDARY
STATUS: Draft
TITLE: Section Body Boundary
STATEMENT: >>>
The body of a recognized or unrecognized heading shall extend from the end of that heading to the beginning of the next supported heading or to the end of the raw input.

Leading and trailing whitespace around each extracted body shall be removed.
<<<
RELATIONS:
- TYPE: Parent
  VALUE: GHOST-PREPROCESS-HEADER-LEVELS

[REQUIREMENT]
UID: GHOST-PREPROCESS-PLAIN-TEXT-MODE
STATUS: Draft
TITLE: Plain-Text Prompt Mode
STATEMENT: >>>
When no supported heading is present, the complete trimmed raw user text shall become the TASK value.

Plain-text mode shall not require schema name matching.
<<<
RELATIONS:
- TYPE: Parent
  VALUE: GHOST-PREPROCESS-NONEMPTY-INPUT

[REQUIREMENT]
UID: GHOST-PREPROCESS-HEADER-RESOLUTION
STATUS: Draft
TITLE: Header Resolution through NameMatcher
STATEMENT: >>>
For structured input, each extracted header title shall be passed through the deterministic name-matching contract before its body can be written into a canonical prompt field.
<<<
RELATIONS:
- TYPE: Parent
  VALUE: GHOST-PREPROCESS-HEADER-LEVELS

[REQUIREMENT]
UID: GHOST-PREPROCESS-LAST-WINS
STATUS: Draft
TITLE: Repeated Canonical Field Handling
STATEMENT: >>>
When multiple headings resolve to the same canonical field, the body of the last occurrence shall replace the earlier occurrence for the current preprocessing run.

The parser shall not concatenate repeated field bodies automatically.
<<<
RELATIONS:
- TYPE: Parent
  VALUE: GHOST-PREPROCESS-HEADER-RESOLUTION

[REQUIREMENT]
UID: GHOST-PREPROCESS-UNKNOWN-HEADERS
STATUS: Draft
TITLE: Unknown Header Handling
STATEMENT: >>>
A header that cannot be resolved through canonical, alias, or bilingual matching shall not create an arbitrary SuperPrompt body field.

Its body shall not overwrite a recognized field.

The current prompt-preparation contract does not require fuzzy recovery of the unknown header.
<<<
RELATIONS:
- TYPE: Parent
  VALUE: GHOST-PREPROCESS-HEADER-RESOLUTION

[REQUIREMENT]
UID: GHOST-PREPROCESS-RECOGNIZED-WRITEBACK
STATUS: Draft
TITLE: Recognized Field Write-Back Only
STATEMENT: >>>
Only values resolved to active runtime prompt fields through the schema-to-runtime mapping shall be eligible for SuperPrompt body write-back.

Schema metadata, unknown headings, and unsupported canonical fields shall not create new dynamic body keys.
<<<
RELATIONS:
- TYPE: Parent
  VALUE: GHOST-PREPROCESS-HEADER-RESOLUTION

[REQUIREMENT]
UID: GHOST-PREPROCESS-TASK-CONTEXT-FALLBACK
STATUS: Draft
TITLE: TASK from CONTEXT Fallback
STATEMENT: >>>
If structured input contains no non-empty TASK but contains a non-empty CONTEXT, the CONTEXT body shall become TASK for the current request.

The consumed CONTEXT shall then be cleared from the current prompt body so that the same text is not presented twice as both TASK and CONTEXT.
<<<
RELATIONS:
- TYPE: Parent
  VALUE: GHOST-PREPROCESS-RECOGNIZED-WRITEBACK

[REQUIREMENT]
UID: GHOST-PREPROCESS-TASK-RAW-FALLBACK
STATUS: Draft
TITLE: TASK from Raw Prompt Fallback
STATEMENT: >>>
If structured input contains neither a non-empty TASK nor a non-empty CONTEXT, the complete trimmed raw user prompt shall become TASK.
<<<
RELATIONS:
- TYPE: Parent
  VALUE: GHOST-PREPROCESS-RECOGNIZED-WRITEBACK

[REQUIREMENT]
UID: GHOST-PREPROCESS-MANDATORY-DEFAULTS
STATUS: Draft
TITLE: Other Mandatory Field Defaults
STATEMENT: >>>
After TASK fallback, each other active mandatory prompt field that remains absent or empty shall receive its configured schema default.

Defaults shall be applied only when the field has an active runtime destination.
<<<
RELATIONS:
- TYPE: Parent
  VALUE: GHOST-PREPROCESS-MUST-DESTINATION

[REQUIREMENT]
UID: GHOST-PREPROCESS-BODY-TEXT-PRESERVATION
STATUS: Draft
TITLE: Prompt Body Text Preservation
STATEMENT: >>>
Deterministic header normalization and matching shall affect header names only.

Recognized section body text shall preserve the user's wording except for outer whitespace trimming and the explicit TASK/CONTEXT fallback behavior.
<<<
RELATIONS:
- TYPE: Parent
  VALUE: GHOST-PREPROCESS-HEADER-RESOLUTION

[[/SECTION]]

[[SECTION]]
TITLE: 5. SuperPrompt Construction and Initial Projection

[TEXT]
STATEMENT: >>>
Deterministic preprocessing updates the existing SuperPrompt in place. It establishes the normalized current request before ActiveBrief routing and A2 shaping occur.
<<<

[REQUIREMENT]
UID: GHOST-PREPROCESS-IN-PLACE-UPDATE
STATUS: Draft
TITLE: In-Place SuperPrompt Update
STATEMENT: >>>
Deterministic preprocessing shall update the SuperPrompt instance supplied by the orchestrator.

It shall not create a hidden parallel prompt object or replace the active SuperPrompt without an explicit orchestration requirement.
<<<
RELATIONS:
- TYPE: Parent
  VALUE: GHOST-PREPROCESS-ROOT

[REQUIREMENT]
UID: GHOST-PREPROCESS-BODY-WRITEBACK
STATUS: Draft
TITLE: Canonical Body Write-Back
STATEMENT: >>>
Recognized and mapped prompt values shall be written into the corresponding active SuperPrompt body fields.

The write-back shall reflect last-wins behavior, TASK fallback, CONTEXT consumption, and active mandatory-field defaults.
<<<
RELATIONS:
- TYPE: Parent
  VALUE: GHOST-PREPROCESS-IN-PLACE-UPDATE

[REQUIREMENT]
UID: GHOST-PREPROCESS-NO-NEW-BODY-FIELDS
STATUS: Draft
TITLE: No Dynamic Body-Field Creation
STATEMENT: >>>
Deterministic preprocessing shall not add new keys outside the active SuperPrompt body contract.

New canonical prompt fields shall require an approved SuperPrompt contract change and explicit schema-to-runtime mapping.
<<<
RELATIONS:
- TYPE: Parent
  VALUE: GHOST-PREPROCESS-BODY-WRITEBACK

[REQUIREMENT]
UID: GHOST-PREPROCESS-PRESERVE-UNTOUCHED-FIELDS
STATUS: Draft
TITLE: Preservation of Untouched Fields
STATEMENT: >>>
A body field not recognized, defaulted, or explicitly cleared by the current preprocessing rules shall retain its existing value.

Prompt preparation shall not clear retrieval artifacts or unrelated SuperPrompt fields merely because preprocessing is re-run.
<<<
RELATIONS:
- TYPE: Parent
  VALUE: GHOST-PREPROCESS-BODY-WRITEBACK

[REQUIREMENT]
UID: GHOST-PREPROCESS-INITIAL-QUERY-PROJECTION
STATUS: Draft
TITLE: Initial Retrieval-Query Projection
STATEMENT: >>>
After deterministic body write-back, GHOST may build an initial retrieval-oriented text projection from TASK, PURPOSE, and CONTEXT.

This initial projection shall not be treated as final until ActiveBrief relation classification and deterministic routing have completed.
<<<
RELATIONS:
- TYPE: Parent
  VALUE: GHOST-PREPROCESS-IN-PLACE-UPDATE

[REQUIREMENT]
UID: GHOST-PREPROCESS-STAGE-MARK
STATUS: Draft
TITLE: Preprocessed Stage Mark
STATEMENT: >>>
Successful deterministic preprocessing of non-empty input shall set SuperPrompt.stage to "preprocessed".
<<<
RELATIONS:
- TYPE: Parent
  VALUE: GHOST-PREPROCESS-IN-PLACE-UPDATE

[REQUIREMENT]
UID: GHOST-PREPROCESS-HISTORY-MARK
STATUS: Draft
TITLE: Preprocessing History Entry
STATEMENT: >>>
Successful deterministic preprocessing of non-empty input shall append "preprocessed" to SuperPrompt.history_of_stages.
<<<
RELATIONS:
- TYPE: Parent
  VALUE: GHOST-PREPROCESS-STAGE-MARK

[REQUIREMENT]
UID: GHOST-PREPROCESS-NO-RETRIEVAL-MUTATION
STATUS: Draft
TITLE: No Retrieval Artifact Mutation
STATEMENT: >>>
Prompt preparation before the retrieval handoff shall not create, rank, remove, or rewrite document chunks, memory candidates, stage ranking views, final document selections, condensed document context, or synthesized memory context.
<<<
RELATIONS:
- TYPE: Parent
  VALUE: GHOST-PREPROCESS-IN-PLACE-UPDATE

[REQUIREMENT]
UID: GHOST-PREPROCESS-LOCAL-PREVIEW
STATUS: Draft
TITLE: Deterministic Intermediate Preview
STATEMENT: >>>
Deterministic preprocessing may create an intermediate prompt preview from the currently populated prompt fields.

That intermediate preview shall not supersede the final centralized projection performed after relation classification and A2 shaping.
<<<
RELATIONS:
- TYPE: Parent
  VALUE: GHOST-PREPROCESS-IN-PLACE-UPDATE

[REQUIREMENT]
UID: GHOST-PREPROCESS-CENTRAL-PROJECTION
STATUS: Draft
TITLE: Central Prompt Projection after Preparation
STATEMENT: >>>
At the completion of the composite preprocessing operation, the controller shall invoke the central SuperPrompt projection path so that prompt_ready reflects the current body fields, evidence policy, ActiveBrief routing state, and current lifecycle state.
<<<
RELATIONS:
- TYPE: Parent
  VALUE: GHOST-PREPROCESS-LOCAL-PREVIEW

[[/SECTION]]

[[SECTION]]
TITLE: 6. ActiveBrief Selection and Classifier Input

[TEXT]
STATEMENT: >>>
After deterministic prompt structuring, GHOST evaluates the current request against the current eligible ActiveBrief when one exists.

ActiveBrief creation and durable memory ownership remain outside this file. This file owns only the selection input needed for relation classification and prompt routing.
<<<

[REQUIREMENT]
UID: GHOST-PREPROCESS-ACTIVEBRIEF-OPTIONAL
STATUS: Draft
TITLE: Optional ActiveBrief Input
STATEMENT: >>>
Prompt preparation shall support execution with or without a configured memory manager and with or without an eligible ActiveBrief.

Absence of an ActiveBrief shall be a valid routing state and shall not be treated as an LLM failure.
<<<
RELATIONS:
- TYPE: Parent
  VALUE: GHOST-PREPROCESS-ROOT

[REQUIREMENT]
UID: GHOST-PREPROCESS-ACTIVEBRIEF-ELIGIBILITY
STATUS: Draft
TITLE: Current Eligible ActiveBrief
STATEMENT: >>>
When a memory manager is available, the classifier input shall use the latest eligible memory record, searched from newest to oldest, that:
- is not tagged Black; and
- contains a non-empty ActiveRetrievalBrief body.

The semantic meaning and lifecycle of memory tags and ActiveRetrievalBrief persistence shall remain owned by the Memory Management requirements.
<<<
RELATIONS:
- TYPE: Parent
  VALUE: GHOST-PREPROCESS-ACTIVEBRIEF-OPTIONAL

[REQUIREMENT]
UID: GHOST-PREPROCESS-ACTIVEBRIEF-SNAPSHOT
STATUS: Draft
TITLE: ActiveBrief Snapshot
STATEMENT: >>>
The relation-classification result shall preserve a snapshot containing the selected ActiveBrief record identifier, title, and body.

If no eligible ActiveBrief exists, the snapshot shall contain empty values rather than an invented brief.
<<<
RELATIONS:
- TYPE: Parent
  VALUE: GHOST-PREPROCESS-ACTIVEBRIEF-ELIGIBILITY

[REQUIREMENT]
UID: GHOST-PREPROCESS-NO-ACTIVEBRIEF-BYPASS
STATUS: Draft
TITLE: No-ActiveBrief Classifier Bypass
STATEMENT: >>>
When no eligible ActiveBrief exists, GHOST shall not invoke the relation-classifier LLM.

It shall record:
- prompt_materiality = UNKNOWN;
- topic_relation = NO_ACTIVEBRIEF;
- relation classifier LLM used = false.
<<<
RELATIONS:
- TYPE: Parent
  VALUE: GHOST-PREPROCESS-ACTIVEBRIEF-OPTIONAL

[REQUIREMENT]
UID: GHOST-PREPROCESS-CLASSIFIER-CURRENT-PROMPT
STATUS: Draft
TITLE: Classifier Current-Prompt Projection
STATEMENT: >>>
When an eligible ActiveBrief exists, the relation classifier shall receive the normalized current prompt built from available PURPOSE, TASK, and CONTEXT values.

The current prompt shall remain distinguishable from the ActiveBrief title and body.
<<<
RELATIONS:
- TYPE: Parent
  VALUE: GHOST-PREPROCESS-ACTIVEBRIEF-ELIGIBILITY

[REQUIREMENT]
UID: GHOST-PREPROCESS-CLASSIFIER-RAW-FALLBACK
STATUS: Draft
TITLE: Classifier Raw-Text Fallback
STATEMENT: >>>
If the normalized PURPOSE, TASK, and CONTEXT projection is empty, the classifier input builder may use the trimmed raw user text as the current prompt.
<<<
RELATIONS:
- TYPE: Parent
  VALUE: GHOST-PREPROCESS-CLASSIFIER-CURRENT-PROMPT

[REQUIREMENT]
UID: GHOST-PREPROCESS-EMPTY-CURRENT-BYPASS
STATUS: Draft
TITLE: Empty Current-Prompt Bypass
STATEMENT: >>>
If an eligible ActiveBrief exists but the classifier current-prompt text remains empty, GHOST shall not invoke the LLM.

It shall deterministically record:
- prompt_materiality = WEAK;
- topic_relation = IRRELEVANT;
- relation classifier LLM used = false.
<<<
RELATIONS:
- TYPE: Parent
  VALUE: GHOST-PREPROCESS-CLASSIFIER-RAW-FALLBACK

[REQUIREMENT]
UID: GHOST-PREPROCESS-ACTIVEBRIEF-OWNERSHIP
STATUS: Draft
TITLE: ActiveBrief Durable-Truth Boundary
STATEMENT: >>>
Prompt preparation shall read the current eligible ActiveBrief for routing but shall not create, update, overwrite, persist, or become the durable owner of the ActiveRetrievalBrief.
<<<
RELATIONS:
- TYPE: Parent
  VALUE: GHOST-PREPROCESS-ACTIVEBRIEF-ELIGIBILITY

[[/SECTION]]

[[SECTION]]
TITLE: 7. ActiveBrief Relation Classification and Deterministic Routing

[TEXT]
STATEMENT: >>>
The relation classifier produces two independent labels. Deterministic policy maps their combination into retrieval-query behavior, final-prompt continuity behavior, and memory-context permission.
<<<

[REQUIREMENT]
UID: GHOST-PREPROCESS-TWO-DIMENSION-CLASSIFICATION
STATUS: Draft
TITLE: Two Independent Classification Dimensions
STATEMENT: >>>
The relation classifier shall return exactly two semantic decisions:
- prompt_materiality; and
- topic_relation.

The classifier shall not collapse both dimensions into one combined LLM label.
<<<
RELATIONS:
- TYPE: Parent
  VALUE: GHOST-PREPROCESS-ROOT

[REQUIREMENT]
UID: GHOST-PREPROCESS-MATERIALITY-CONTRACT
STATUS: Draft
TITLE: Prompt Materiality Contract
STATEMENT: >>>
Prompt materiality shall be classified from the current prompt alone.

Allowed values shall be:
- STRONG: the current prompt independently identifies a task, topic, or information need;
- WEAK: the current prompt depends mainly on previous conversational context.

Relation to the ActiveBrief shall not by itself make a prompt STRONG.
<<<
RELATIONS:
- TYPE: Parent
  VALUE: GHOST-PREPROCESS-TWO-DIMENSION-CLASSIFICATION

[REQUIREMENT]
UID: GHOST-PREPROCESS-RELATION-CONTRACT
STATUS: Draft
TITLE: Topic Relation Contract
STATEMENT: >>>
Topic relation shall be classified using both the current prompt and the ActiveBrief.

Allowed values shall be:
- SAME_TOPIC: direct continuation or clear reference to the current ActiveBrief topic;
- RELATED_DOMAIN: a different immediate topic within the same broader professional or technical domain;
- IRRELEVANT: another domain or no useful contextual bridge.
<<<
RELATIONS:
- TYPE: Parent
  VALUE: GHOST-PREPROCESS-TWO-DIMENSION-CLASSIFICATION

[REQUIREMENT]
UID: GHOST-PREPROCESS-CLASSIFICATION-ORDER
STATUS: Draft
TITLE: Classification Decision Order
STATEMENT: >>>
The classifier instruction shall require prompt materiality to be decided first from the current prompt alone and topic relation to be decided second using the current prompt and ActiveBrief.
<<<
RELATIONS:
- TYPE: Parent
  VALUE: GHOST-PREPROCESS-TWO-DIMENSION-CLASSIFICATION

[REQUIREMENT]
UID: GHOST-PREPROCESS-CLASSIFIER-CONFIG
STATUS: Draft
TITLE: Configured Relation Classifier
STATEMENT: >>>
The current relation classifier shall be represented by a versioned Agent Stack configuration defining:
- classifier identity;
- model settings;
- static classifier rules;
- ActiveBrief and current-prompt bindings;
- the two decision targets; and
- the structured output mapping.

The functional behavior in this file shall remain independent of the physical JSON path.
<<<
RELATIONS:
- TYPE: Parent
  VALUE: GHOST-PREPROCESS-TWO-DIMENSION-CLASSIFICATION

[REQUIREMENT]
UID: GHOST-PREPROCESS-CLASSIFIER-STRUCTURED-OUTPUT
STATUS: Draft
TITLE: Exact Classifier Output
STATEMENT: >>>
The relation-classifier LLM shall return one JSON object containing exactly:
- prompt_materiality; and
- topic_relation.

It shall not return action decisions, explanations, prose, or additional keys as part of the required output contract.
<<<
RELATIONS:
- TYPE: Parent
  VALUE: GHOST-PREPROCESS-CLASSIFIER-CONFIG

[REQUIREMENT]
UID: GHOST-PREPROCESS-CLASSIFIER-VALIDATION
STATUS: Draft
TITLE: Classifier Result Validation
STATEMENT: >>>
After AgentPrompt parsing, GHOST shall validate that prompt_materiality and topic_relation belong to their exact allowed value sets.

An invalid or unknown value shall fail explicitly and shall not be converted into a fabricated valid routing state.
<<<
RELATIONS:
- TYPE: Parent
  VALUE: GHOST-PREPROCESS-CLASSIFIER-STRUCTURED-OUTPUT

[REQUIREMENT]
UID: GHOST-PREPROCESS-RELATION-STATE
STATUS: Draft
TITLE: Combined Relation State
STATEMENT: >>>
For an eligible ActiveBrief, GHOST shall derive a combined relation-state identifier from prompt_materiality and topic_relation.

For absence of an ActiveBrief, the relation state shall be NO_ACTIVEBRIEF.
<<<
RELATIONS:
- TYPE: Parent
  VALUE: GHOST-PREPROCESS-TWO-DIMENSION-CLASSIFICATION

[REQUIREMENT]
UID: GHOST-PREPROCESS-DECISION-CONTRACT
STATUS: Draft
TITLE: Deterministic Routing Decision Contract
STATEMENT: >>>
GHOST shall deterministically derive one routing decision containing:
- prompt_materiality;
- topic_relation;
- use_activebrief_for_retrieval;
- final_prompt_mode;
- allow_memory_context; and
- memory_context_policy.

The LLM shall not populate these action fields directly.
<<<
RELATIONS:
- TYPE: Parent
  VALUE: GHOST-PREPROCESS-TWO-DIMENSION-CLASSIFICATION

[REQUIREMENT]
UID: GHOST-PREPROCESS-STATE-NO-ACTIVEBRIEF
STATUS: Draft
TITLE: Routing State: No ActiveBrief
STATEMENT: >>>
For NO_ACTIVEBRIEF, GHOST shall set:
- use_activebrief_for_retrieval = false;
- final_prompt_mode = none;
- allow_memory_context = true;
- memory_context_policy = normal_no_activebrief.

The effective document query shall use the current prompt only.
<<<
RELATIONS:
- TYPE: Parent
  VALUE: GHOST-PREPROCESS-DECISION-CONTRACT

[REQUIREMENT]
UID: GHOST-PREPROCESS-STATE-STRONG-SAME
STATUS: Draft
TITLE: Routing State: Strong and Same Topic
STATEMENT: >>>
For STRONG + SAME_TOPIC, GHOST shall set:
- use_activebrief_for_retrieval = false;
- final_prompt_mode = full_activebrief;
- allow_memory_context = true;
- memory_context_policy = allowed.

The effective document query shall use the current prompt without adding the ActiveBrief.
<<<
RELATIONS:
- TYPE: Parent
  VALUE: GHOST-PREPROCESS-DECISION-CONTRACT

[REQUIREMENT]
UID: GHOST-PREPROCESS-STATE-WEAK-SAME
STATUS: Draft
TITLE: Routing State: Weak and Same Topic
STATEMENT: >>>
For WEAK + SAME_TOPIC, GHOST shall set:
- use_activebrief_for_retrieval = true;
- final_prompt_mode = full_activebrief;
- allow_memory_context = true;
- memory_context_policy = allowed.

The effective document query shall contain the current prompt and the full ActiveBrief body.
<<<
RELATIONS:
- TYPE: Parent
  VALUE: GHOST-PREPROCESS-DECISION-CONTRACT

[REQUIREMENT]
UID: GHOST-PREPROCESS-STATE-STRONG-RELATED
STATUS: Draft
TITLE: Routing State: Strong and Related Domain
STATEMENT: >>>
For STRONG + RELATED_DOMAIN, GHOST shall set:
- use_activebrief_for_retrieval = false;
- final_prompt_mode = title_related_domain_note;
- allow_memory_context = true;
- memory_context_policy = allowed_related_domain.

The effective document query shall use the current prompt without adding the ActiveBrief.
<<<
RELATIONS:
- TYPE: Parent
  VALUE: GHOST-PREPROCESS-DECISION-CONTRACT

[REQUIREMENT]
UID: GHOST-PREPROCESS-STATE-WEAK-RELATED
STATUS: Draft
TITLE: Routing State: Weak and Related Domain
STATEMENT: >>>
For WEAK + RELATED_DOMAIN, GHOST shall set:
- use_activebrief_for_retrieval = true;
- final_prompt_mode = title_related_domain_note;
- allow_memory_context = true;
- memory_context_policy = allowed_related_domain.

The effective document query shall contain the current prompt and the ActiveBrief title, but not the full ActiveBrief body.
<<<
RELATIONS:
- TYPE: Parent
  VALUE: GHOST-PREPROCESS-DECISION-CONTRACT

[REQUIREMENT]
UID: GHOST-PREPROCESS-STATE-STRONG-IRRELEVANT
STATUS: Draft
TITLE: Routing State: Strong and Irrelevant
STATEMENT: >>>
For STRONG + IRRELEVANT, GHOST shall set:
- use_activebrief_for_retrieval = false;
- final_prompt_mode = title_topic_shift_note;
- allow_memory_context = false;
- memory_context_policy = disabled.

The effective document query shall use the current prompt without adding the ActiveBrief.
<<<
RELATIONS:
- TYPE: Parent
  VALUE: GHOST-PREPROCESS-DECISION-CONTRACT

[REQUIREMENT]
UID: GHOST-PREPROCESS-STATE-WEAK-IRRELEVANT
STATUS: Draft
TITLE: Routing State: Weak and Irrelevant
STATEMENT: >>>
For WEAK + IRRELEVANT, GHOST shall set:
- use_activebrief_for_retrieval = false;
- final_prompt_mode = none;
- allow_memory_context = false;
- memory_context_policy = disabled.

The effective document-retrieval query shall be empty, signaling that document retrieval is not applicable for this state.
<<<
RELATIONS:
- TYPE: Parent
  VALUE: GHOST-PREPROCESS-DECISION-CONTRACT

[REQUIREMENT]
UID: GHOST-PREPROCESS-FINAL-MODE-AUTHORITY
STATUS: Draft
TITLE: Final Prompt Mode Authority
STATEMENT: >>>
Central prompt projection shall honor the deterministic final_prompt_mode stored by prompt preparation.

The projector shall not independently derive an ActiveBrief inclusion behavior that contradicts the routing decision.

The supported current modes shall mean:
- full_activebrief: include title and full brief as supporting continuity context;
- title_related_domain_note: include the title with related-domain continuity framing;
- title_topic_shift_note: include the title only for explicit topic-shift awareness;
- none: include no ActiveBrief content.
<<<
RELATIONS:
- TYPE: Parent
  VALUE: GHOST-PREPROCESS-DECISION-CONTRACT

[REQUIREMENT]
UID: GHOST-PREPROCESS-MEMORY-POLICY-AUTHORITY
STATUS: Draft
TITLE: Memory Context Permission Authority
STATEMENT: >>>
Downstream Memory Management shall honor allow_memory_context and memory_context_policy from the deterministic routing decision.

A disabled memory-context state shall not be overridden by generic memory retrieval merely because memory data is available.
<<<
RELATIONS:
- TYPE: Parent
  VALUE: GHOST-PREPROCESS-DECISION-CONTRACT

[REQUIREMENT]
UID: GHOST-PREPROCESS-ROUTING-EXTRAS
STATUS: Draft
TITLE: Relation and Routing Metadata in SuperPrompt
STATEMENT: >>>
Prompt preparation shall expose the relation-classification and routing result through stable SuperPrompt extras sufficient for downstream traceability.

The current contract shall include:
- activebrief_prompt_materiality;
- activebrief_topic_relation;
- activebrief_relation_state;
- activebrief_relation_llm_used;
- activebrief_relation_decision;
- activebrief_relation_activebrief.
<<<
RELATIONS:
- TYPE: Parent
  VALUE: GHOST-PREPROCESS-DECISION-CONTRACT

[REQUIREMENT]
UID: GHOST-PREPROCESS-ROUTING-LOG
STATUS: Draft
TITLE: Public Relation Summary
STATEMENT: >>>
Prompt preparation shall emit a compact user-visible summary of the current topic relation and prompt strength after the routing result is written.

Detailed prompts, ActiveBrief bodies, or raw model output shall not be exposed through the public log solely to explain the classification.
<<<
RELATIONS:
- TYPE: Parent
  VALUE: GHOST-PREPROCESS-DECISION-CONTRACT

[[/SECTION]]

[[SECTION]]
TITLE: 8. A2 PromptShaper and Job Structuring

[TEXT]
STATEMENT: >>>
A2 PromptShaper refines the prepared request into explicit meta-configuration for downstream answering and evidence handling.

A2 is a concrete selector consumer of the neutral Agent Stack. Its functional semantics and deterministic safety layer are defined here.
<<<

[REQUIREMENT]
UID: GHOST-PREPROCESS-A2-INPUT-STATE
STATUS: Draft
TITLE: A2 Input State
STATEMENT: >>>
A2 shall operate on a SuperPrompt that has completed deterministic preprocessing and ActiveBrief routing.

Its semantic input shall be derived from the current TASK, PURPOSE, and CONTEXT rather than from retrieved document chunks or synthesized memory context.
<<<
RELATIONS:
- TYPE: Parent
  VALUE: GHOST-PREPROCESS-ROOT

[REQUIREMENT]
UID: GHOST-PREPROCESS-A2-CONFIG
STATUS: Draft
TITLE: Versioned A2 Configuration
STATEMENT: >>>
A2 shall obtain its prompt contract and option catalogs from a versioned Agent Stack configuration.

The configuration shall define the A2 identity, selector mode, model settings, static decision rules, dynamic bindings, decision targets, output mappings, and allowed option catalogs.
<<<
RELATIONS:
- TYPE: Parent
  VALUE: GHOST-PREPROCESS-A2-INPUT-STATE

[REQUIREMENT]
UID: GHOST-PREPROCESS-A2-TARGETS
STATUS: Draft
TITLE: A2 Decision Targets
STATEMENT: >>>
The current A2 PromptShaper shall classify these six fields:
- system;
- audience;
- tone;
- depth;
- confidence;
- evidence_policy.

System may select one to three configured role identifiers. Each other field shall select exactly one configured identifier.
<<<
RELATIONS:
- TYPE: Parent
  VALUE: GHOST-PREPROCESS-A2-CONFIG

[REQUIREMENT]
UID: GHOST-PREPROCESS-A2-PAYLOAD
STATUS: Draft
TITLE: A2 Runtime Payload
STATEMENT: >>>
A2 shall build its prompt-under-evaluation from the available PURPOSE, TASK, and CONTEXT values of the current SuperPrompt.

A2 shall also provide an explicit required-output JSON shape derived from the active configured decision targets.
<<<
RELATIONS:
- TYPE: Parent
  VALUE: GHOST-PREPROCESS-A2-INPUT-STATE

[REQUIREMENT]
UID: GHOST-PREPROCESS-A2-LLM-MODE
STATUS: Draft
TITLE: A2 LLM Selector Mode
STATEMENT: >>>
When A2 LLM mode is enabled, A2 shall:
1. obtain the configured AgentPrompt;
2. compose the selector messages;
3. call the configured LLM path;
4. parse the structured result; and
5. apply deterministic selector sanitization before SuperPrompt write-back.
<<<
RELATIONS:
- TYPE: Parent
  VALUE: GHOST-PREPROCESS-A2-CONFIG

[REQUIREMENT]
UID: GHOST-PREPROCESS-A2-DEFAULT-MODE
STATUS: Draft
TITLE: A2 Deterministic-Default Mode
STATEMENT: >>>
When A2 LLM mode is disabled, A2 shall construct its candidate selector result deterministically from configured defaults.

If a configured default is absent, A2 may use the first allowed configured option or the allowed prefix required by a multi-selection target.

The same deterministic sanitization and write-back rules shall apply after candidate construction.
<<<
RELATIONS:
- TYPE: Parent
  VALUE: GHOST-PREPROCESS-A2-CONFIG

[REQUIREMENT]
UID: GHOST-PREPROCESS-A2-MODEL-SETTINGS
STATUS: Draft
TITLE: A2 Configured Model Settings
STATEMENT: >>>
A2 shall use model name, temperature where applicable, and maximum output-token allowance obtained from its AgentPrompt configuration.

A2 business logic shall not silently replace configured model settings with unrelated hard-coded values.
<<<
RELATIONS:
- TYPE: Parent
  VALUE: GHOST-PREPROCESS-A2-CONFIG

[REQUIREMENT]
UID: GHOST-PREPROCESS-A2-STRUCTURED-OUTPUT
STATUS: Draft
TITLE: A2 Structured Selector Output
STATEMENT: >>>
A2 shall request and parse a JSON object using only configured output keys and allowed option identifiers.

The model output shall not be written directly into SuperPrompt before deterministic sanitization.
<<<
RELATIONS:
- TYPE: Parent
  VALUE: GHOST-PREPROCESS-A2-LLM-MODE

[REQUIREMENT]
UID: GHOST-PREPROCESS-A2-INVALID-REMOVAL
STATUS: Draft
TITLE: A2 Invalid Identifier Removal
STATEMENT: >>>
For each A2 field, deterministic sanitization shall remove option identifiers that are not present in that field's allowed catalog.

This rule shall remove invented identifiers, malformed identifiers, and identifiers copied from another field's catalog.
<<<
RELATIONS:
- TYPE: Parent
  VALUE: GHOST-PREPROCESS-A2-STRUCTURED-OUTPUT

[REQUIREMENT]
UID: GHOST-PREPROCESS-A2-DUPLICATE-REMOVAL
STATUS: Draft
TITLE: A2 Duplicate Identifier Removal
STATEMENT: >>>
Deterministic A2 sanitization shall remove duplicate option identifiers while preserving the first valid occurrence order.
<<<
RELATIONS:
- TYPE: Parent
  VALUE: GHOST-PREPROCESS-A2-STRUCTURED-OUTPUT

[REQUIREMENT]
UID: GHOST-PREPROCESS-A2-CARDINALITY
STATUS: Draft
TITLE: A2 Cardinality Enforcement
STATEMENT: >>>
A2 sanitization shall enforce each active field's configured maximum selection count.

When more valid identifiers are returned than allowed, the first valid identifiers up to the configured maximum shall be retained.
<<<
RELATIONS:
- TYPE: Parent
  VALUE: GHOST-PREPROCESS-A2-STRUCTURED-OUTPUT

[REQUIREMENT]
UID: GHOST-PREPROCESS-A2-EMPTY-PRESERVE
STATUS: Draft
TITLE: Preserve Existing Value after Empty Sanitization
STATEMENT: >>>
If an A2 field has no valid identifier after sanitization, A2 shall omit that field from write-back.

A2 shall preserve the existing preprocessing value and shall not apply a catalog default as semantic repair after invalid LLM output.
<<<
RELATIONS:
- TYPE: Parent
  VALUE: GHOST-PREPROCESS-A2-STRUCTURED-OUTPUT

[REQUIREMENT]
UID: GHOST-PREPROCESS-A2-ID-LABEL-SEPARATION
STATUS: Draft
TITLE: A2 Identifier and Display-Label Separation
STATEMENT: >>>
A2 shall preserve selected option identifiers in SuperPrompt extras for traceability.

When a configured display label exists, the corresponding human-readable label shall be written into the SuperPrompt body field.

For multi-selected system roles, the body value shall contain the ordered selected labels in a readable joined form.
<<<
RELATIONS:
- TYPE: Parent
  VALUE: GHOST-PREPROCESS-A2-STRUCTURED-OUTPUT

[REQUIREMENT]
UID: GHOST-PREPROCESS-A2-EXTRAS
STATUS: Draft
TITLE: A2 Diagnostic Metadata
STATEMENT: >>>
A2 shall write stable runtime metadata sufficient to identify:
- the sanitized selected identifiers;
- whether the LLM was used; and
- whether execution used LLM mode or deterministic-default mode.

Current keys shall include a2_selected_ids, a2_llm_used, and a2_mode.
<<<
RELATIONS:
- TYPE: Parent
  VALUE: GHOST-PREPROCESS-A2-ID-LABEL-SEPARATION

[REQUIREMENT]
UID: GHOST-PREPROCESS-A2-BODY-WRITEBACK
STATUS: Draft
TITLE: A2 Body Write-Back
STATEMENT: >>>
A2 shall update only active target fields that retain valid sanitized values.

A2 shall not overwrite TASK, PURPOSE, CONTEXT, FORMAT, TEXT, document context, memory context, or ActiveBrief routing metadata as a side effect of meta-field selection.
<<<
RELATIONS:
- TYPE: Parent
  VALUE: GHOST-PREPROCESS-A2-ID-LABEL-SEPARATION

[REQUIREMENT]
UID: GHOST-PREPROCESS-A2-STAGE
STATUS: Draft
TITLE: A2 Stage Mark
STATEMENT: >>>
After successful A2 processing, SuperPrompt.stage shall be set to "a2".
<<<
RELATIONS:
- TYPE: Parent
  VALUE: GHOST-PREPROCESS-A2-BODY-WRITEBACK

[REQUIREMENT]
UID: GHOST-PREPROCESS-A2-HISTORY
STATUS: Draft
TITLE: A2 History Entry
STATEMENT: >>>
After successful A2 processing, "a2" shall be appended to SuperPrompt.history_of_stages.
<<<
RELATIONS:
- TYPE: Parent
  VALUE: GHOST-PREPROCESS-A2-STAGE

[REQUIREMENT]
UID: GHOST-PREPROCESS-A2-PROJECTION
STATUS: Draft
TITLE: A2 Prompt Projection
STATEMENT: >>>
After A2 write-back, GHOST shall rebuild prompt_ready through the current central SuperPrompt composition contract so that selected meta-field labels and evidence policy are visible in the prepared prompt preview.
<<<
RELATIONS:
- TYPE: Parent
  VALUE: GHOST-PREPROCESS-A2-BODY-WRITEBACK

[REQUIREMENT]
UID: GHOST-PREPROCESS-A2-NO-RETRIEVAL-MUTATION
STATUS: Draft
TITLE: A2 Retrieval-State Preservation
STATEMENT: >>>
A2 shall not create, remove, reorder, or rewrite document retrieval results, memory retrieval results, evidence selections, condensed context, or retrieval-stage score views.
<<<
RELATIONS:
- TYPE: Parent
  VALUE: GHOST-PREPROCESS-A2-BODY-WRITEBACK

[REQUIREMENT]
UID: GHOST-PREPROCESS-A2-RERUN
STATUS: Draft
TITLE: Safe A2 Re-Execution
STATEMENT: >>>
The orchestrator may re-run A2 after preprocessing when meta-field refinement is required.

Re-running A2 shall apply the same sanitization and write-back rules and shall not clear existing retrieval artifacts solely because the lifecycle stage returns to "a2".
<<<
RELATIONS:
- TYPE: Parent
  VALUE: GHOST-PREPROCESS-A2-BODY-WRITEBACK

[[/SECTION]]

[[SECTION]]
TITLE: 9. Prepared Handoff to Knowledge and Memory Retrieval

[TEXT]
STATEMENT: >>>
The prompt-preparation capability finishes when the structured current request, routing policy, A2 meta-configuration, effective retrieval query, and prompt preview are mutually consistent.
<<<

[REQUIREMENT]
UID: GHOST-PREPROCESS-QUERY-FINALIZATION
STATUS: Draft
TITLE: Post-Classification Retrieval-Query Finalization
STATEMENT: >>>
After ActiveBrief relation classification and deterministic routing, GHOST shall rebuild SuperPrompt.effective_retrieval_query_text from the final routing state.

The query stored for downstream document retrieval shall not remain an earlier pre-classification projection when the final state requires ActiveBrief inclusion or retrieval suppression.
<<<
RELATIONS:
- TYPE: Parent
  VALUE: GHOST-PREPROCESS-ROOT

[REQUIREMENT]
UID: GHOST-PREPROCESS-QUERY-SOURCE
STATUS: Draft
TITLE: Retrieval Query Source Fields
STATEMENT: >>>
The current prompt portion of the effective retrieval query shall be derived from available TASK, PURPOSE, and CONTEXT values.

A2 meta-fields such as system, audience, tone, depth, confidence, and evidence_policy shall not be inserted into the document-retrieval query merely because they appear in the final prompt preview.
<<<
RELATIONS:
- TYPE: Parent
  VALUE: GHOST-PREPROCESS-QUERY-FINALIZATION

[REQUIREMENT]
UID: GHOST-PREPROCESS-QUERY-ACTIVEBRIEF
STATUS: Draft
TITLE: ActiveBrief Contribution to Retrieval Query
STATEMENT: >>>
ActiveBrief content shall contribute to the effective retrieval query only according to the deterministic routing state:
- WEAK + SAME_TOPIC: full ActiveBrief body;
- WEAK + RELATED_DOMAIN: ActiveBrief title;
- all STRONG states: no ActiveBrief contribution;
- WEAK + IRRELEVANT: empty query;
- NO_ACTIVEBRIEF: current prompt only.
<<<
RELATIONS:
- TYPE: Parent
  VALUE: GHOST-PREPROCESS-QUERY-FINALIZATION

[REQUIREMENT]
UID: GHOST-PREPROCESS-KNOWLEDGE-HANDOFF
STATUS: Draft
TITLE: Knowledge Retrieval Handoff
STATEMENT: >>>
The Knowledge Management path shall receive:
- the prepared SuperPrompt;
- the synchronized effective retrieval-query text; and
- routing state sufficient to determine whether document retrieval is applicable.

This handoff shall not precompute document candidates.
<<<
RELATIONS:
- TYPE: Parent
  VALUE: GHOST-PREPROCESS-QUERY-FINALIZATION

[REQUIREMENT]
UID: GHOST-PREPROCESS-MEMORY-HANDOFF
STATUS: Draft
TITLE: Memory Retrieval Handoff
STATEMENT: >>>
The Memory Management path shall receive:
- the prepared SuperPrompt;
- the ActiveBrief snapshot and relation state;
- allow_memory_context; and
- memory_context_policy.

This handoff shall not precompute or synthesize memory context.
<<<
RELATIONS:
- TYPE: Parent
  VALUE: GHOST-PREPROCESS-QUERY-FINALIZATION

[REQUIREMENT]
UID: GHOST-PREPROCESS-EMPTY-QUERY-SIGNAL
STATUS: Draft
TITLE: Empty Retrieval Query as Suppression Signal
STATEMENT: >>>
An empty effective document-retrieval query produced by WEAK + IRRELEVANT routing shall be treated as an explicit document-retrieval suppression signal.

Downstream orchestration shall skip document retrieval or handle the state without attempting a normal retrieval call with an empty query.
<<<
RELATIONS:
- TYPE: Parent
  VALUE: GHOST-PREPROCESS-QUERY-FINALIZATION

[REQUIREMENT]
UID: GHOST-PREPROCESS-HANDOFF-CONSISTENCY
STATUS: Draft
TITLE: Prepared-State Consistency
STATEMENT: >>>
At handoff, the following shall describe the same current request and routing decision:
- SuperPrompt body fields;
- ActiveBrief relation extras;
- deterministic routing decision;
- effective retrieval-query text;
- A2 selected identifiers and display labels;
- lifecycle stage and history;
- prompt_ready.

Contradictory representations shall be treated as a defect.
<<<
RELATIONS:
- TYPE: Parent
  VALUE: GHOST-PREPROCESS-QUERY-FINALIZATION

[REQUIREMENT]
UID: GHOST-PREPROCESS-NO-KNOWLEDGE-EXECUTION
STATUS: Draft
TITLE: No Knowledge Retrieval Execution
STATEMENT: >>>
The prompt-preparation capability shall not query ChromaDB, SPLADE indexes, document manifests, rerankers, A3, or A4.
<<<
RELATIONS:
- TYPE: Parent
  VALUE: GHOST-PREPROCESS-KNOWLEDGE-HANDOFF

[REQUIREMENT]
UID: GHOST-PREPROCESS-NO-MEMORY-EXECUTION
STATUS: Draft
TITLE: No Memory Retrieval Execution
STATEMENT: >>>
The prompt-preparation capability shall not query memory vector stores, run memory candidate scoring, merge memory records, or synthesize final memory context.

Reading the current eligible ActiveBrief for relation classification shall not be treated as full Memory Retrieval execution.
<<<
RELATIONS:
- TYPE: Parent
  VALUE: GHOST-PREPROCESS-MEMORY-HANDOFF

[REQUIREMENT]
UID: GHOST-PREPROCESS-CURRENT-REQUEST-PRIORITY
STATUS: Draft
TITLE: Current Request Priority in Prepared Prompt
STATEMENT: >>>
The prepared prompt preview shall present the current user request as the highest-priority task.

Any ActiveBrief continuity material shall be presented only as supporting context according to final_prompt_mode.
<<<
RELATIONS:
- TYPE: Parent
  VALUE: GHOST-PREPROCESS-HANDOFF-CONSISTENCY

[[/SECTION]]

[[SECTION]]
TITLE: 10. Error Handling, Logging, and Quality Requirements

[TEXT]
STATEMENT: >>>
Prompt preparation combines deterministic logic with two bounded LLM-enabled functions. Failures shall remain explicit, observable, and traceable without fabricating successful routing or shaping results.
<<<

[REQUIREMENT]
UID: GHOST-PREPROCESS-SCHEMA-ERROR
STATUS: Draft
TITLE: Prompt Schema Failure
STATEMENT: >>>
A missing, unreadable, malformed, or non-object prompt schema shall fail explicitly during schema initialization.

GHOST shall not silently continue with an invented schema when deterministic preprocessing depends on that configuration.
<<<
RELATIONS:
- TYPE: Parent
  VALUE: GHOST-PREPROCESS-ROOT

[REQUIREMENT]
UID: GHOST-PREPROCESS-CLASSIFIER-ERROR
STATUS: Draft
TITLE: Relation Classifier Failure Integrity
STATEMENT: >>>
A provider failure, parse failure, missing required binding, or invalid classifier value shall not produce a fabricated STRONG, WEAK, SAME_TOPIC, RELATED_DOMAIN, or IRRELEVANT result.

Fallback behavior, if introduced later, shall require an explicit approved requirement.
<<<
RELATIONS:
- TYPE: Parent
  VALUE: GHOST-PREPROCESS-ROOT

[REQUIREMENT]
UID: GHOST-PREPROCESS-A2-ERROR
STATUS: Draft
TITLE: A2 Failure Integrity
STATEMENT: >>>
A2 provider or parse failure shall not be represented as a successful LLM selection.

The deterministic-default mode shall be used only when explicitly selected by the caller, not as an undisclosed replacement for a failed LLM call.
<<<
RELATIONS:
- TYPE: Parent
  VALUE: GHOST-PREPROCESS-ROOT

[REQUIREMENT]
UID: GHOST-PREPROCESS-NO-UNNECESSARY-CLASSIFIER-CALL
STATUS: Draft
TITLE: No Unnecessary Relation-Classifier Call
STATEMENT: >>>
GHOST shall not invoke the relation-classifier LLM when no eligible ActiveBrief exists or when the classifier current-prompt text is empty.
<<<
RELATIONS:
- TYPE: Parent
  VALUE: GHOST-PREPROCESS-ROOT

[REQUIREMENT]
UID: GHOST-PREPROCESS-LOGGING-BOUNDARY
STATUS: Draft
TITLE: Prompt Preparation Logging Boundary
STATEMENT: >>>
Prompt preparation shall emit compact public lifecycle and relation summaries and may emit richer internal or developer diagnostics according to the logging policy.

Raw prompt payloads, ActiveBrief bodies, model messages, and raw model outputs shall not be exposed through public logs by default.
<<<
RELATIONS:
- TYPE: Parent
  VALUE: GHOST-PREPROCESS-ROOT

[REQUIREMENT]
UID: GHOST-PREPROCESS-DETERMINISTIC-REPRODUCIBILITY
STATUS: Draft
TITLE: Deterministic Reproducibility
STATEMENT: >>>
Given the same raw prompt, prompt schema, starting relevant SuperPrompt body state, and no LLM-enabled step, deterministic preprocessing shall produce the same recognized field values and routing-independent intermediate query text.
<<<
RELATIONS:
- TYPE: Parent
  VALUE: GHOST-PREPROCESS-ROOT

[REQUIREMENT]
UID: GHOST-PREPROCESS-TESTABILITY
STATUS: Draft
TITLE: Prompt Function Testability
STATEMENT: >>>
Prompt parsing, name resolution, schema-to-runtime mapping, TASK fallback, routing-table construction, query projection, A2 sanitization, and SuperPrompt write-back shall be testable independently of the GUI.

LLM-enabled classifier and A2 tests shall support provider stubs or recorded structured responses so deterministic post-processing can be verified.
<<<
RELATIONS:
- TYPE: Parent
  VALUE: GHOST-PREPROCESS-ROOT

[REQUIREMENT]
UID: GHOST-PREPROCESS-NO-HIDDEN-HEURISTICS
STATUS: Draft
TITLE: No Hidden Prompt Heuristics
STATEMENT: >>>
Current prompt-preparation behavior shall not depend on undocumented fuzzy matching, semantic thresholds, hidden prompt repairs, or implicit ActiveBrief inclusion rules.

Every current deterministic action shall be traceable to an explicit requirement and testable rule.
<<<
RELATIONS:
- TYPE: Parent
  VALUE: GHOST-PREPROCESS-ROOT

[[/SECTION]]

[[SECTION]]
TITLE: 11. Traceability and Sibling Requirement Ownership

[TEXT]
STATEMENT: >>>
The current implementation trace anchors for this requirement area are:

- ragstream/preprocessing/preprocessing.py
- ragstream/preprocessing/prompt_schema.py
- ragstream/preprocessing/name_matcher.py
- ragstream/preprocessing/activebrief_relation_classifier.py
- ragstream/config/prompt_schema.json
- data/agents/activebrief_relation_classifier/activebrief_relation_classifier_001.json
- ragstream/agents/a2_promptshaper.py
- data/agents/a2_promptshaper/003.json
- data/agents/a2_promptshaper/a2_catalogs/003_option_catalogs_system.json
- data/agents/a2_promptshaper/a2_catalogs/003_option_catalogs_rest.json
- ragstream/orchestration/super_prompt.py
- ragstream/orchestration/superprompt_projector.py
- ragstream/app/controller.py

These are trace anchors, not a replacement for the normative requirements in this file.
<<<

[REQUIREMENT]
UID: GHOST-PREPROCESS-CODE-TRACE-ANCHORS
STATUS: Draft
TITLE: Prompt Function Code Trace Anchors
STATEMENT: >>>
Prompt-preparation requirements shall remain traceable to the modules and configurations that implement schema loading, deterministic parsing, name matching, ActiveBrief relation classification, A2 shaping, SuperPrompt mutation, query projection, and controller coordination.

A private helper shall not become the owner of a system requirement merely because it currently contains the implementing function.
<<<
RELATIONS:
- TYPE: Parent
  VALUE: GHOST-PREPROCESS-ROOT

[REQUIREMENT]
UID: GHOST-PREPROCESS-SIBLING-OWNERSHIP
STATUS: Draft
TITLE: Sibling Requirement Ownership
STATEMENT: >>>
Detailed behavior shall remain in the following sibling requirement areas:

- neutral AgentFactory, AgentPrompt, and LLMClient infrastructure in 20_agent_stack.sdoc;
- runtime stage coordination in 10_orchestrator_and_pipeline.sdoc;
- document ingestion in 41_document_ingestion.sdoc;
- document retrieval and reranking in 42_document_retrieval_and_reranking.sdoc;
- document usefulness selection and condensation in 43_evidence_selection_and_condensation.sdoc;
- memory recording and ActiveBrief creation/update in 51_memory_recording_and_files.sdoc;
- memory ingestion and retrieval in 52_memory_ingestion_and_retrieval.sdoc;
- memory merge, ActiveBrief continuity, and Blackboard direction in 53_memory_merge_activebrief_blackboard.sdoc;
- current Streamlit controls and preview rendering in 61_streamlit_workbench_current.sdoc;
- logging in 81_logging_textforge_raglog.sdoc;
- security and traceability governance in 83_quality_security_traceability_governance.sdoc.

This file shall not duplicate those subsystem algorithms.
<<<
RELATIONS:
- TYPE: Parent
  VALUE: GHOST-PREPROCESS-ROOT

[REQUIREMENT]
UID: GHOST-PREPROCESS-CHANGE-SYNCHRONIZATION
STATUS: Draft
TITLE: Requirement and Implementation Synchronization
STATEMENT: >>>
An approved change to prompt schema semantics, deterministic parsing, canonical field mapping, ActiveBrief routing, A2 targets, query projection, public interfaces, or SuperPrompt write-back shall update the affected requirements and verification assets together with the implementation change.

Private refactoring that preserves required behavior and interfaces shall not require new functional requirements.

Code that contradicts an approved requirement in this file shall be treated as a defect or unapproved change until the contradiction is resolved.
<<<
RELATIONS:
- TYPE: Parent
  VALUE: GHOST-PREPROCESS-CODE-TRACE-ANCHORS

[REQUIREMENT]
UID: GHOST-PREPROCESS-CURRENT-FUTURE-BOUNDARY
STATUS: Draft
TITLE: Current and Future Prompt-Function Boundary
STATEMENT: >>>
The current requirement baseline shall not present the following as implemented unless corresponding code and tests exist:
- fuzzy or edit-distance header matching;
- semantic or LLM-based header recovery;
- template or keyword-cue field inference;
- automatic multi-pass A2 refinement;
- new prompt body fields without SuperPrompt support;
- new relation labels or routing states;
- retrieval or memory algorithms inside preprocessing.

Such capabilities shall be introduced through explicit future requirements and controlled implementation changes.
<<<
RELATIONS:
- TYPE: Parent
  VALUE: GHOST-PREPROCESS-ROOT

[[/SECTION]]

[[SECTION]]
TITLE: 12. Acceptance Criteria

[TEXT]
STATEMENT: >>>
These acceptance criteria validate the complete prompt-preparation path without duplicating the internal acceptance criteria of the Agent Stack, Knowledge Management, or Memory Management subsystems.
<<<

[REQUIREMENT]
UID: GHOST-PREPROCESS-AC-WHITESPACE
STATUS: Draft
TITLE: AC: Whitespace-Only Input
STATEMENT: >>>
Given whitespace-only raw input, the controller shall return the existing SuperPrompt without invoking deterministic preprocessing, relation classification, or A2 and without appending a new preprocessing history entry.
<<<
RELATIONS:
- TYPE: Parent
  VALUE: GHOST-PREPROCESS-NONEMPTY-INPUT

[REQUIREMENT]
UID: GHOST-PREPROCESS-AC-PLAIN-TASK
STATUS: Draft
TITLE: AC: Plain Text Becomes TASK
STATEMENT: >>>
Given raw input with no supported heading, deterministic preprocessing shall write the complete trimmed input into SuperPrompt.body["task"], set stage to preprocessed, append the preprocessing history entry, and preserve retrieval artifacts.
<<<
RELATIONS:
- TYPE: Parent
  VALUE: GHOST-PREPROCESS-PLAIN-TEXT-MODE

[REQUIREMENT]
UID: GHOST-PREPROCESS-AC-CANONICAL-HEADER
STATUS: Draft
TITLE: AC: Canonical Header Resolution
STATEMENT: >>>
Given a supported heading named TASK, the parser shall resolve it canonically and write its body into the runtime task field.
<<<
RELATIONS:
- TYPE: Parent
  VALUE: GHOST-PREPROCESS-CANONICAL-MATCH

[REQUIREMENT]
UID: GHOST-PREPROCESS-AC-ALIAS-HEADER
STATUS: Draft
TITLE: AC: Alias Header Resolution
STATEMENT: >>>
Given a heading named Objective and an alias mapping from objective to purpose, the parser shall write the heading body into the runtime purpose field.
<<<
RELATIONS:
- TYPE: Parent
  VALUE: GHOST-PREPROCESS-ALIAS-MATCH

[REQUIREMENT]
UID: GHOST-PREPROCESS-AC-BILINGUAL-HEADER
STATUS: Draft
TITLE: AC: Bilingual Header Resolution
STATEMENT: >>>
Given a heading named Aufgabe and a configured German mapping from aufgabe to task, the parser shall write the heading body into the runtime task field.
<<<
RELATIONS:
- TYPE: Parent
  VALUE: GHOST-PREPROCESS-BILINGUAL-MATCH

[REQUIREMENT]
UID: GHOST-PREPROCESS-AC-NORMALIZATION
STATUS: Draft
TITLE: AC: Header-Key Normalization
STATEMENT: >>>
Given two header names that differ only by case, Unicode compatibility form, outer whitespace, internal whitespace runs, or punctuation removed by the normalization contract, they shall resolve to the same normalized matching key.
<<<
RELATIONS:
- TYPE: Parent
  VALUE: GHOST-PREPROCESS-SCHEMA-NORMALIZATION

[REQUIREMENT]
UID: GHOST-PREPROCESS-AC-LAST-WINS
STATUS: Draft
TITLE: AC: Repeated Field Last Wins
STATEMENT: >>>
Given two supported headings that both resolve to task, the body of the second occurrence shall become the final task value for that preprocessing run.
<<<
RELATIONS:
- TYPE: Parent
  VALUE: GHOST-PREPROCESS-LAST-WINS

[REQUIREMENT]
UID: GHOST-PREPROCESS-AC-CONTEXT-FALLBACK
STATUS: Draft
TITLE: AC: CONTEXT Promoted to TASK
STATEMENT: >>>
Given structured input with no non-empty TASK and one non-empty CONTEXT, the CONTEXT body shall become TASK and the current runtime CONTEXT shall be cleared.
<<<
RELATIONS:
- TYPE: Parent
  VALUE: GHOST-PREPROCESS-TASK-CONTEXT-FALLBACK

[REQUIREMENT]
UID: GHOST-PREPROCESS-AC-RAW-FALLBACK
STATUS: Draft
TITLE: AC: Raw Prompt TASK Fallback
STATEMENT: >>>
Given structured input with neither non-empty TASK nor non-empty CONTEXT, the complete trimmed raw input shall become TASK.
<<<
RELATIONS:
- TYPE: Parent
  VALUE: GHOST-PREPROCESS-TASK-RAW-FALLBACK

[REQUIREMENT]
UID: GHOST-PREPROCESS-AC-UNKNOWN-HEADER
STATUS: Draft
TITLE: AC: Unknown Header Isolation
STATEMENT: >>>
Given an unrecognized heading, deterministic preprocessing shall not create a new SuperPrompt body key and shall not overwrite a recognized canonical field.
<<<
RELATIONS:
- TYPE: Parent
  VALUE: GHOST-PREPROCESS-UNKNOWN-HEADERS

[REQUIREMENT]
UID: GHOST-PREPROCESS-AC-SCHEMA-RUNTIME-MAP
STATUS: Draft
TITLE: AC: Schema-to-Runtime Mapping
STATEMENT: >>>
Given a recognized response_depth or output_format value, prompt preprocessing shall route it to runtime depth or format respectively.

A configured mandatory field without a runtime destination shall fail requirement conformance rather than being reported as enforced.
<<<
RELATIONS:
- TYPE: Parent
  VALUE: GHOST-PREPROCESS-SCHEMA-RUNTIME-MAPPING

[REQUIREMENT]
UID: GHOST-PREPROCESS-AC-NO-ACTIVEBRIEF
STATUS: Draft
TITLE: AC: No ActiveBrief State
STATEMENT: >>>
Given no eligible ActiveBrief, relation classification shall not call the LLM and shall write UNKNOWN, NO_ACTIVEBRIEF, an empty ActiveBrief snapshot, and the normal_no_activebrief routing decision.
<<<
RELATIONS:
- TYPE: Parent
  VALUE: GHOST-PREPROCESS-STATE-NO-ACTIVEBRIEF

[REQUIREMENT]
UID: GHOST-PREPROCESS-AC-EMPTY-CURRENT
STATUS: Draft
TITLE: AC: Empty Current Prompt with ActiveBrief
STATEMENT: >>>
Given an eligible ActiveBrief but no usable current-prompt text, relation classification shall not call the LLM and shall write WEAK + IRRELEVANT with memory context disabled and final_prompt_mode none.
<<<
RELATIONS:
- TYPE: Parent
  VALUE: GHOST-PREPROCESS-EMPTY-CURRENT-BYPASS

[REQUIREMENT]
UID: GHOST-PREPROCESS-AC-CLASSIFIER-VALUES
STATUS: Draft
TITLE: AC: Exact Relation Classifier Values
STATEMENT: >>>
Given a normal relation-classifier call, the accepted parsed result shall contain one allowed prompt_materiality value and one allowed topic_relation value.

Any other value shall fail explicitly before routing action fields are written as a valid decision.
<<<
RELATIONS:
- TYPE: Parent
  VALUE: GHOST-PREPROCESS-CLASSIFIER-VALIDATION

[REQUIREMENT]
UID: GHOST-PREPROCESS-AC-SIX-STATE-MATRIX
STATUS: Draft
TITLE: AC: Six-State Deterministic Routing Matrix
STATEMENT: >>>
Given each valid STRONG/WEAK and SAME_TOPIC/RELATED_DOMAIN/IRRELEVANT combination, GHOST shall produce exactly the routing values defined in the corresponding state requirement.

The same classification pair shall always produce the same routing decision.
<<<
RELATIONS:
- TYPE: Parent
  VALUE: GHOST-PREPROCESS-DECISION-CONTRACT

[REQUIREMENT]
UID: GHOST-PREPROCESS-AC-WEAK-SAME-QUERY
STATUS: Draft
TITLE: AC: Weak Same-Topic Retrieval Query
STATEMENT: >>>
Given WEAK + SAME_TOPIC and a non-empty ActiveBrief body, the finalized effective retrieval query shall include the current TASK/PURPOSE/CONTEXT projection and the full ActiveBrief body.
<<<
RELATIONS:
- TYPE: Parent
  VALUE: GHOST-PREPROCESS-STATE-WEAK-SAME

[REQUIREMENT]
UID: GHOST-PREPROCESS-AC-WEAK-RELATED-QUERY
STATUS: Draft
TITLE: AC: Weak Related-Domain Retrieval Query
STATEMENT: >>>
Given WEAK + RELATED_DOMAIN and a non-empty ActiveBrief title, the finalized effective retrieval query shall include the current TASK/PURPOSE/CONTEXT projection and the ActiveBrief title without the full ActiveBrief body.
<<<
RELATIONS:
- TYPE: Parent
  VALUE: GHOST-PREPROCESS-STATE-WEAK-RELATED

[REQUIREMENT]
UID: GHOST-PREPROCESS-AC-WEAK-IRRELEVANT-QUERY
STATUS: Draft
TITLE: AC: Weak Irrelevant Retrieval Suppression
STATEMENT: >>>
Given WEAK + IRRELEVANT, the finalized effective document-retrieval query shall be empty and memory context shall be disabled.
<<<
RELATIONS:
- TYPE: Parent
  VALUE: GHOST-PREPROCESS-STATE-WEAK-IRRELEVANT

[REQUIREMENT]
UID: GHOST-PREPROCESS-AC-QUERY-REBUILD
STATUS: Draft
TITLE: AC: Query Rebuilt after Classification
STATEMENT: >>>
Given an initial pre-classification query and a final routing state that changes ActiveBrief contribution or suppresses retrieval, the effective retrieval-query field shall be rebuilt after classification and shall reflect the final state at handoff.
<<<
RELATIONS:
- TYPE: Parent
  VALUE: GHOST-PREPROCESS-QUERY-FINALIZATION

[REQUIREMENT]
UID: GHOST-PREPROCESS-AC-FINAL-MODE
STATUS: Draft
TITLE: AC: Final Prompt Mode Projection
STATEMENT: >>>
Given a deterministic final_prompt_mode, the central projector shall include exactly the permitted ActiveBrief continuity material for that mode and shall not independently apply a contradictory state table.
<<<
RELATIONS:
- TYPE: Parent
  VALUE: GHOST-PREPROCESS-FINAL-MODE-AUTHORITY

[REQUIREMENT]
UID: GHOST-PREPROCESS-AC-A2-INVALID
STATUS: Draft
TITLE: AC: A2 Invalid Identifier Sanitization
STATEMENT: >>>
Given an A2 result containing an invented identifier or an identifier from another field's catalog, the sanitizer shall remove that identifier before SuperPrompt write-back.
<<<
RELATIONS:
- TYPE: Parent
  VALUE: GHOST-PREPROCESS-A2-INVALID-REMOVAL

[REQUIREMENT]
UID: GHOST-PREPROCESS-AC-A2-PRESERVE
STATUS: Draft
TITLE: AC: A2 Empty Sanitized Field Preservation
STATEMENT: >>>
Given an A2 field whose candidate output becomes empty after sanitization, A2 shall preserve the existing preprocessing value by omitting that field from write-back.
<<<
RELATIONS:
- TYPE: Parent
  VALUE: GHOST-PREPROCESS-A2-EMPTY-PRESERVE

[REQUIREMENT]
UID: GHOST-PREPROCESS-AC-A2-DEFAULT
STATUS: Draft
TITLE: AC: A2 Deterministic-Default Mode
STATEMENT: >>>
Given use_llm = false and valid configured defaults, A2 shall produce a sanitized selector result without an LLM call, mark a2_llm_used false, and mark its mode as deterministic_defaults.
<<<
RELATIONS:
- TYPE: Parent
  VALUE: GHOST-PREPROCESS-A2-DEFAULT-MODE

[REQUIREMENT]
UID: GHOST-PREPROCESS-AC-A2-ID-LABEL
STATUS: Draft
TITLE: AC: A2 Identifier and Label Write-Back
STATEMENT: >>>
Given valid sanitized A2 identifiers with configured labels, SuperPrompt extras shall retain the identifiers while the body fields contain their human-readable labels.
<<<
RELATIONS:
- TYPE: Parent
  VALUE: GHOST-PREPROCESS-A2-ID-LABEL-SEPARATION

[REQUIREMENT]
UID: GHOST-PREPROCESS-AC-A2-STATE
STATUS: Draft
TITLE: AC: A2 Lifecycle and Artifact Preservation
STATEMENT: >>>
After successful A2 execution, stage shall equal a2, history shall contain the new a2 entry, prompt_ready shall reflect the A2 selections, and existing document or memory retrieval artifacts shall remain unchanged.
<<<
RELATIONS:
- TYPE: Parent
  VALUE: GHOST-PREPROCESS-A2-STAGE

[REQUIREMENT]
UID: GHOST-PREPROCESS-AC-HANDOFF
STATUS: Draft
TITLE: AC: Prepared Retrieval Handoff
STATEMENT: >>>
At completion of prompt preparation, the SuperPrompt body, routing extras, effective retrieval query, A2 metadata, stage/history, and prompt_ready shall be mutually consistent and sufficient for Knowledge and Memory Retrieval to begin without reparsing the raw user prompt.
<<<
RELATIONS:
- TYPE: Parent
  VALUE: GHOST-PREPROCESS-HANDOFF-CONSISTENCY

[REQUIREMENT]
UID: GHOST-PREPROCESS-AC-NO-RETRIEVAL
STATUS: Draft
TITLE: AC: No Retrieval inside Prompt Preparation
STATEMENT: >>>
Executing the complete prompt-preparation capability shall not query document or memory vector stores and shall not run reranking, A3, A4, or memory synthesis.
<<<
RELATIONS:
- TYPE: Parent
  VALUE: GHOST-PREPROCESS-NO-KNOWLEDGE-EXECUTION

[REQUIREMENT]
UID: GHOST-PREPROCESS-AC-SYNCHRONIZATION
STATUS: Draft
TITLE: AC: Requirement-Code Synchronization
STATEMENT: >>>
An implementation baseline shall not be accepted when its prompt-schema mapping, routing table, query projection, final prompt projection, or A2 sanitization contradicts an approved requirement in this file.

The contradiction shall be resolved by correcting the defect or approving a coordinated requirement and implementation change.
<<<
RELATIONS:
- TYPE: Parent
  VALUE: GHOST-PREPROCESS-CHANGE-SYNCHRONIZATION

[[/SECTION]]

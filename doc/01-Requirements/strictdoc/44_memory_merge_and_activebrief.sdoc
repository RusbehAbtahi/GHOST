[DOCUMENT]
TITLE: Memory Merge and ActiveBrief Requirements
UID: GHOST-REQ-MEMORY-MERGE-ACTIVEBRIEF
VERSION: 0.1-dummy
OPTIONS:
  MARKUP: Text
  AUTO_LEVELS: On
  NODE_IN_TOC: True

[[SECTION]]
TITLE: Placeholder

[TEXT]
STATEMENT: >>>
This is a placeholder child requirements document for GHOST MemoryMerge and ActiveBrief behavior.

Planned scope:
- runtime memory compression
- MemoryMerge synthesis
- ActiveBrief relation classification
- contributor IDs
- retrieval routing signals
- comparison-context construction

Detailed atomic requirements shall be added later after human approval.
<<<

[[/SECTION]]
